(DEFUN SUMA (P VX VY)
  (SETQ X (CAR P))
  (SETQ Y (CAR (CDR P)))
  (LIST (+ X VX) (+ Y VY) (LAST P))
)

(defun equis ()
  (if (< xmayor (atof dat))
    (setq xmayor (atof dat))
  )
  (if (> xmenor (atof dat))
    (setq xmenor (atof dat))
  )
)

(defun ye ()
  (if (< ymayor (atof dat))
    (setq ymayor (atof dat))
  )
  (if (> ymenor (atof dat))
    (setq ymenor (atof dat))
  )
)


(DEFUN COLUMNAS ()
  (SETQ CA (SUBSTR LIN 1 1))
  (SETQ C 0) (SETQ X 1)
  (setq xmayor 0) (setq xmenor 0) (setq ymayor 0) (setq ymenor 0)
  (WHILE (/= C 3)
    (SETQ C (+ C 1))
    (SETQ DAT "")
    (WHILE (/= CA ",")
      (SETQ X (+ X 1))
      (SETQ DAT (STRCAT DAT CA))
      (SETQ CA (SUBSTR LIN X 1))
    )
    (SETQ CA "")
    (if (= c 1)
      (equis)
    )
    (if (= c 2)
      (ye)
    )
  )
)


(DEFUN LEE ()
  (SETQ LIN (READ-LINE arch))
  (SETQ L 1)
  (LEEINI)
  (WHILE (AND LIN (<= L FIN))
    (COLUMNAS)
    (SETQ L (+ L 1))
    (SETQ LIN (READ-LINE arch))
  )
  (SETQ L (- L 1))
  (command p)
)

(defun camatr ()
  (setq atrib (cdr (assoc 2 (entget ent))))
  (setq nocol (cdr (assoc atrib datos)))
  (setq valor (cdr (assoc nocol atributos)))
  (entmod (subst (cons 1 valor)
                 (assoc 1 (entget ent))
                 (entget ent)
          )
  )
)

(defun cambiaatr ()
  (setq ent (entlast))
  (while ent
    (if (= "ATTRIB" (cdr (assoc 0 (entget ent))))
      (camatr)
    )
    (setq ent (entnext ent))
  )
)

(DEFUN COLUMNAS2 ()
  (SETQ CA (SUBSTR LIN 1 1))
  (SETQ C 0) (SETQ X 1)
  (SETQ ATRIBUTOS NIL)
  (WHILE (/= C (+ noatri 3))
    (SETQ C (+ C 1))
    (SETQ DAT "")
    (SETQ SALIR "N")
    (WHILE SALIR
      (SETQ X (+ X 1))
      (SETQ DAT (STRCAT DAT CA))
      (SETQ CA (SUBSTR LIN X 1))
      (IF (= CA ",")
        (SETQ SALIR nil)
      )
      (IF (= CA "")
        (SETQ SALIR nil)
      )
    )
    (SETQ CA "")
    (setq atributo (cons c dat))
    (setq atributos (append atributos (list atributo)))
  )
;  (IF (= "3" TRI)
;    (COMMAND "COPY" UL "" (LIST ex ey) (LIST (ATOF (CDR (ASSOC 1 ATRIBUTOS)))
;                                             (ATOF (CDR (ASSOC 2 ATRIBUTOS)))
;                                             (ATOF (CDR (ASSOC 3 ATRIBUTOS)))))
;    (COMMAND "COPY" UL "" (LIST ex ey) (LIST (ATOF (CDR (ASSOC 1 ATRIBUTOS)))
;                                             (ATOF (CDR (ASSOC 2 ATRIBUTOS)))))
;  )
;  (cambiaatr)
  (SETQ CODIGOA CODIGO)
  (SETQ PA P)
  (SETQ P (STRCAT (CDR (ASSOC 1 ATRIBUTOS)) "," (CDR (ASSOC 2 ATRIBUTOS)) "," (CDR (ASSOC 3 ATRIBUTOS))))
  (SETQ CODIGO (CDR (ASSOC 5 ATRIBUTOS)))
  (SETQ CODIGOP (SUBSTR CODIGO 1 5))
  (setq p2 (list (atof (CDR (ASSOC 1 ATRIBUTOS))) (atof (CDR (ASSOC 2 ATRIBUTOS))) (atof (CDR (ASSOC 3 ATRIBUTOS)))))
  (command p)
;  (print p2)
;  (if (or (= codigoP "arbol") (= codigoP "ARBOL"))
;     (COMMAND "INSERT" (STRCAT RUTA "BLOCKS\\ARBOL.dwg") P "" "" "")
;  )                         ' INSERTA ARBOL
;  (IF (= CODIGO CODIGOA) (SETQ LPROV "1"))
;  (IF (/= LPROV NIL)
;    (if (= union "1")
;      (IF (AND (= CODIGO CODIGOA) (/= CODIGOP "ARBOL") (/= CODIGO "Z") (/= CODIGO "EST"))
;        (UNE)
;        (UNESEG)
;      )
;    )
;  )
)

(DEFUN LEEINI ()
 (if (/= oldop "todo")
  (progn
   (WHILE (< L INI)
     (SETQ L (+ L 1))
     (SETQ LIN (READ-LINE arch))
   )
   (SETQ LIN (READ-LINE arch))
  )
 )
)

(DEFUN LEE2 ()
  (SETQ LIN (READ-LINE arch))
  (SETQ L 1) (setq atributos nil)
  (LEEINI)
  (if (/= oldop "todo")
    (WHILE (AND LIN (<= L FIN))
      (COLUMNAS2)
      (SETQ L (+ L 1))
      (SETQ LIN (READ-LINE arch))
    )
    (WHILE LIN 
      (COLUMNAS2)
      (SETQ LIN (READ-LINE arch))
    )
  )
  (SETQ L (- L 1))
)

(defun proatrib ()
  (setq noatri (+ noatri 1))
  (setq nomatr (cdr (assoc 2 (entget e))))
  (print nomatr)
  (IF (= 1 NOATRI)
    (SETQ K 5)
  )
  (IF (= 2 NOATRI)
    (SETQ K 3)
  )
  (IF (= 3 NOATRI)
    (SETQ K 4)
  )
  (IF (= OPINSAT 0)
    (SETQ COLUMNA K)
    (setq columna (getint (STRCAT " No. de columna para este atributo <" (ITOA K) "> : ")))
  )
  (IF (= COLUMNA NIL) 
    (SETQ COLUMNA K)
  )
  (setq dato (cons nomatr columna))
  (setq datos (append datos (list dato)))
)

(defun abloque ()
  (setq e (cdr (assoc -2 lisblo)))
  (setq lstattrib nil)
  (setq noatri 0) (setq datos nil)
  (while e
    (if (= "ATTDEF" (cdr (assoc 0 (entget e))))
      (PROATRIB)
    )
    (setq e (entnext e))
  )
  (print noatri)
)

(defun contINS ()
  (COMMAND "UNDO" "M")
  (if (= fechains nil)
    (progn
      (COMMAND "SHELL" (strcat RUTA "fecha2"))
      (command "delay" 100)
      (setq fechains "y")
    )
  )
  (C:LIBRERIA "busca block en base de datos")
  (C:LIBRERIA "Carga blocks a pplt")
  (C:LIBRERIA "Carga LAYERs a pplt")
  (C:LIBRERIA "lee valor de texto de pplt")
  (C:LIBRERIA "BUSCA LAYER EN BASE DE DATOS")
  (C:LIBRERIA "lee valor numerico de pplt")
  (command "layer" "M" "LINEAS" "C" "GREEN" "LINEAS" "")
  (SETQ VALIDA (SBLBD "PUN2"))
    (If (/= VALIDA "S") 
      (PROGN 
       (COMMAND "INSERT" (STRCAT RUTA "BLOCKS\\PUN2.dwg") "0,0" "" "" "" "" "" "" "" "" "")
       (COMMAND "ERASE" (ENTLAST) "")
      )
    )
  (SETQ VALIDA (SBLBD "PUNTO"))
    (If (/= VALIDA "S") 
      (PROGN 
       (COMMAND "INSERT" (STRCAT RUTA "BLOCKS\\PUNTO.dwg") "0,0" "" "" "" "" "" "" "" "" "")
       (COMMAND "ERASE" (ENTLAST) "")
      )
    )
  (setq ARCINSAT (open (strcat ruta "configuraciones de programas\\INSATR.CFG") "r"))
  (IF (= ARCINSAT NIL)
   (PROGN
    (SETQ NBLOCK "PUN2")
    (SETQ ESCB 1.00)
    (SETQ ARCHIVOP "c:\\TOPOGRAF\\PROV.CSV")
    (SETQ RI 1)
    (SETQ RF 1000)
    (SETQ DIMEN "2")
   )
   (PROGN
    (setq NBLOCK (read-line arCINSAT))
    (setq ESCB (read-line arcINSAT))
    (if (/= escb nil)
      (SETQ ESCB (ATOF ESCB))
      (SETQ ESCB 1.0)
    )
    (setq ARCHIVOP (read-line arCINSAT))
    (setq RI (read-line arcINSAT))
    (if (/= ri nil)
      (SETQ RI (ATOI RI))
      (SETQ RI 1)
    )
    (setq RF (read-line arcINSAT))
    (if (/= rf nil)
      (SETQ Rf (ATOI Rf))
      (SETQ Rf 1000)
    )
    (setq DIMEN (read-line arCINSAT))
    (IF (= Nblock NIL) (SETQ Nblock "pun2"))
    (IF (= archivop NIL) (SETQ archivop "c:\\topograf\\prov.csv"))
    (IF (= dimen NIL) (SETQ dimen "2"))
    (CLOSE ARCINSAT)
   )
  )
  (setq NOMARCH (getfiled "ARCHIVO DE DATOS" ARCHIVOP "CSV" 32))
;  (WHILE (= NOMARCH NIL)
;    (setq NOMARCH (getfiled "SELECCIONA EL ARCHIVO DE DATOS" ARCHIVOP "CSV" 32))
;  )
  (if (= NOMARCH NIL)
    (exit)
  )
  (setq ARCdate (open "c:\\date.tmp" "r"))
  (setq fecha (read-line arcdate))
  (close arcdate)
  (setq archivop nomarch)
  (setq dcl_id (load_dialog (strcat ruta "dialogos\\insatr.dcl"))) ; Load the DCL file.
  (if (not (new_dialog "insatr" dcl_id))   ; Initialize the dialog.
    (exit)                                ; Exit if this doesn't 
                                          ; work.
  )
  (setq numerofinallista (ldblpp "Nblock"))
  (setq numerofinallista2 (ldlApp "Nlayer"))
  (if (= (strcase nblock) "PUN2")
    (set_tile "Nblock" "0")
  )
  (SET_TILE "Nlayer" (itoa (rnnpp (getvar "CLAYER") "C:\\PROVL.TMP")))
  (set_tile "Arcf" archivop)
  (set_tile "Nblock" nblock)
  (set_tile "Sblock" (rtos Escb 2 3))
  (set_tile "Old" "1")
  (set_tile "tag2" "1")
  (set_tile "une" "1")
  (set_tile "layer2" "1")
  (set_tile "fecha" fecha)
  (mode_tile "Iniciol" 1)
  (mode_tile "finl" 1)
  (mode_tile "tag1" 1)
  (mode_tile "tag2" 1)
  (mode_tile "Cadena" 1)
  (set_tile "Iniciol" (itoa RI))
  (set_tile "finl" (itoa RF))
  (if (/= dimen "2")
     (set_tile "tres" "1")
     (set_tile "dos" "1")
  )
  (action_tile "examinaf" "(examinaf2)")
  (action_tile "Old2" "(mode_tile_on)")
  (action_tile "Old" "(mode_tile_off)")
  (action_tile "layer1" "(mode_tile_l1)")
  (action_tile "camcolor" "(cambiacolor)")
  (action_tile "layer2" "(mode_tile_l2)")
  (action_tile "tag1" "(st_tile_pr)")
  (action_tile "tag2" "(st_tile_pr)")
  (action_tile "Cadena" "(st_tile_pr)")
  (action_tile "examina" "(examinaf)")
  (action_tile "attrib" "(attributo)")
  (action_tile "accept" "(leevar)")
  (action_tile "cancel" "(exit)")
  (start_dialog)                          ; Display the dialog 
                                          ; box.
  (unload_dialog dcl_id)                  ; Unload the DCL file.
  (princ)
  (if (= oplayer "1")
    (command "layer" "M" nombrelmk "" "s" nombrelmk "")
    (command "layer" "s" nlayer "")
  )

  (setq ex 1.13)
  (setq ey 1.13) 
  (setq tt ESCB)
    (SETQ OPCIONESOS (GETVAR "OSMODE"))
    (command "osnap" "none")
    (SETQ VALIDA (SBLBD (STRCASE nomblo)))
    (IF (/= "S" VALIDA) (SETQ VALIDA (SBLBD NOMBLO)))
    (If (/= VALIDA "S") 
      (PROGN 
       (if (= (substr nomblo 2 1) ":")
         (COMMAND "INSERT" nomblo "0,0" "" "" "" "" "" "" "" "" "" "" "" "" "" "" "")
         (COMMAND "INSERT" (STRCAT RUTA "BLOCKS\\" nomblo ".dwg") "0,0" "" "" "" "" "" "" "" "" "" "" "" "" "" "" "")
       )
       (setq nomblo (cdr (assoc 2 (entget (entlast)))))
       (COMMAND "ERASE" (ENTLAST) "")
      )
    )
  (command "INSERT" nomblo (list ex ey) tt "" ""
   "" "" "" "" "" "" "" "" "" "" "" "" "" "" "" "" "" "" "" "" "" "" "" ""
   "" "" "" "" "" "" "" "" "" "" "" "" "" "" "" "" "" "" "" "" "" "" "" "")
  (SETQ UL (ENTLAST))
  (IF (/= resultado8 "1")
    (setq TRI "3")
    (setq TRI "2")
  )
  (IF (= resultado4 "1")
    (setq oldop "todo")
    (setq oldop "bloque")
  )
  (setq ARCINSAT (open (strcat ruta "configuraciones de programas\\INSATR.CFG") "w"))
  (WRITE-LINE NOMBLO ARCINSAT)
  (WRITE-LINE (RTOS tt 2 3) ARCINSAT)
  (WRITE-LINE NOMARCH ARCINSAT)
  (WRITE-LINE (RTOS INI 2 3) ARCINSAT)
  (WRITE-LINE (RTOS FIN 2 3) ARCINSAT)
  (WRITE-LINE tri ARCINSAT)
  (CLOSE ARCINSAT)
  (setq lisblo (tblsearch "block" nomblo))
  (ABLOQUE)
;  (IF (/= (SUBSTR ARCHIVOP 1 1) (CHR 34)))
;    (SETQ ARCHIVOP (STRCAT (CHR 34) ARCHIVOP (CHR 34)))
;  )
  (setq arch (OPEN NOMARCH "r"))
  (command "3dmesh" "34" "32")
  (if arch
    (LEE)
    (print "\n Archivo no encontrado ")
  )
  (close arch)
;  (command "ZOOM" "w" (list xmayor ymayor) (list xmenor ymenor))
  (setq arch (OPEN NOMARCH "r"))
  (if arch
    (LEE2)
  )
  (close arch)
  (entdel ul)
  (SETVAR "OSMODE" OPCIONESOS)
  (command "ZOOM" "E")
)

(defun c:insat ()
  (SETQ CODIGOA "")
  (SETQ CODIGO "")
  (SETQ LPROV NIL)
  (contINS)
)

(defun examinaf ()
  (setq archbl (getfiled "Block a insertar" (strcat ruta "blocks\\" nblock ".dwg") "dwg" 32))
  (WHILE (= ARCHBL NIL)
    (setq ARCHBL (getfiled "Block a insertar" (strcat ruta "blocks\\" nblock ".dwg") "DWG" 32))
  )
  (start_list "Nblock" 2)
  (add_list archbl)
  (end_list)
  (setq archdim (open "c:\\prov.tmp" "a"))
  (write-line archbl archdim)
  (close archdim)
  (set_tile "Nblock" (itoa numerofinallista))
  (setq numerofinallista (1+ numerofinallista))
)

(defun examinaf2 ()
  (setq NOMARCH2 (getfiled "Archivo Fuente" ARCHIVOP "CSV" 32))
  (WHILE (= NOMARCH2 NIL)
    (setq NOMARCH2 (getfiled "SELECCIONA EL ARCHIVO DE DATOS" ARCHIVOP "CSV" 32))
  )
  (setq NOMARCh NOMARCH2)
  (set_tile "Arcf" Nomarch)
)

(defun leevar ()
  (setq nomarch (get_tile "Arcf"))
  (setq nomblo (get_tile "Nblock"))
  (setq nomblo (rblpp (atoi nomblo) "C:\\PROV.TMP"))
  (setq nly (get_tile "Nlayer"))
  (setq nlayer (rblpp (atoi nly) "C:\\PROVl.TMP"))
  (setq escb (atof (get_tile "Sblock")))
  (setq resultado4 (get_tile "Old"))
  (setq ini (get_tile "Iniciol"))
  (setq ini (atoi ini))
  (setq fin (get_tile "finl"))
  (setq fin (atoi fin))
  (setq resultado8 (get_tile "dos"))
  (setq oplayer (get_tile "layer1"))
  (setq nombrelmk (get_tile "Prevcad"))
  (setq union (get_tile "une"))
  (done_dialog)
)

(defun mode_tile_on()
  (mode_tile "Iniciol" 0)
  (mode_tile "finl" 0)
)

(defun mode_tile_off()
  (mode_tile "Iniciol" 1)
  (mode_tile "finl" 1)
)

(defun mode_tile_l1 ()
  (mode_tile "tag1" 0)
  (mode_tile "tag2" 0)
  (mode_tile "Cadena" 0)
  (mode_tile "Nlayer" 1)
)

(defun mode_tile_l2 ()
  (mode_tile "tag1" 1)
  (mode_tile "tag2" 1)
  (mode_tile "Cadena" 1)
  (mode_tile "Nlayer" 0)
)

(defun st_tile_pr ()
  (setq cadprov "")
  (if (= (get_tile "tag1") "1")
    (setq cadprov fecha)
  )
  (if (= (get_tile "tag2") "1")
    (setq cadprov (strcat cadprov (get_tile "Cadena")))
  )
  (set_tile "Prevcad" cadprov)
  (SETQ OPPRV (BSLAYER cadprov))
  (if (= opprv "S") (alert "Nombre de layer repetido"))
)

(DEFUN UNE ()
  (command "LAYER" "S" "LINEAS" "")
  (COMMAND "PLINE" P PA "")
  (SETQ ULLI (ENTLAST))
  (setq paso 1)
;  (command "LAYER" "S" "0" "")
)

(DEFUN UNESEG ()
  (if (= paso 1)
    (COMMAND "PEDIT" ULLI "J" "ALL" "" "")
  )
)

(defun attributo ()
  (setq arch (OPEN NOMARCH "r"))
  (setq linea1 (read-line arch))
  (setq linea2 (read-line arch))
  (setq linea3 (read-line arch))
  (setq linea4 (read-line arch))
  (setq linea5 (read-line arch))
  (setq linea6 (read-line arch))
  (setq linea7 (read-line arch))
  (setq linea8 (read-line arch))
  (setq linea9 (read-line arch))
  (setq linea10 (read-line arch))
  (close arch)
  (convierte)
  (if (not (new_dialog "insatr2" dcl_id))   ; Initialize the dialog.   2do dialogo
    (exit)                                ; Exit if this doesn't 
                                          ; work.
  )
  (set_tile "t1" linea1)
  (set_tile "t2" linea2)
  (set_tile "t3" linea3)
  (set_tile "t4" linea4)
  (set_tile "t5" linea5)
  (set_tile "t6" linea6)
  (set_tile "t7" linea7)
  (set_tile "t8" linea8)
  (set_tile "t9" linea9)
  (set_tile "t10" linea10)
  (start_dialog)                          ; Display the dialog 
  (if (not (new_dialog "insatr" dcl_id))   ; Initialize the dialog.
    (exit)                                ; Exit if this doesn't 
                                          ; work.
  )
  (setq numerofinallista (ldblpp "Nblock"))
  (setq numerofinallista2 (ldlApp "Nlayer"))
  (if (= (strcase nblock) "PUN2")
    (set_tile "Nblock" "0")
  )
  (SET_TILE "Nlayer" (itoa (rnnpp (getvar "CLAYER") "C:\\PROVL.TMP")))
  (set_tile "Arcf" archivop)
  (set_tile "Nblock" nblock)
  (set_tile "Sblock" (rtos Escb 2 3))
  (set_tile "Old" "1")
  (set_tile "tag2" "1")
  (set_tile "une" "1")
  (set_tile "layer2" "1")
  (set_tile "fecha" fecha)
  (mode_tile "Iniciol" 1)
  (mode_tile "finl" 1)
  (mode_tile "tag1" 1)
  (mode_tile "tag2" 1)
  (mode_tile "Cadena" 1)
  (set_tile "Iniciol" (itoa RI))
  (set_tile "finl" (itoa RF))
  (if (/= dimen "2")
     (set_tile "tres" "1")
     (set_tile "dos" "1")
  )
  (action_tile "examinaf" "(examinaf2)")
  (action_tile "Old2" "(mode_tile_on)")
  (action_tile "Old" "(mode_tile_off)")
  (action_tile "layer1" "(mode_tile_l1)")
  (action_tile "camcolor" "(cambiacolor)")
  (action_tile "layer2" "(mode_tile_l2)")
  (action_tile "tag1" "(st_tile_pr)")
  (action_tile "tag2" "(st_tile_pr)")
  (action_tile "Cadena" "(st_tile_pr)")
  (action_tile "examina" "(examinaf)")
  (action_tile "attrib" "(attributo)")
  (action_tile "accept" "(leevar)")
  (action_tile "cancel" "(exit)")
  (start_dialog)                          ; Display the dialog 
  (done_dialog)
)

(defun convierte ()
   (setq linea1 (comasxspc linea1))
   (setq linea2 (comasxspc linea2))
   (setq linea3 (comasxspc linea3))
   (setq linea4 (comasxspc linea4))
   (setq linea5 (comasxspc linea5))
   (setq linea6 (comasxspc linea6))
   (setq linea7 (comasxspc linea7))
   (setq linea8 (comasxspc linea8))
   (setq linea9 (comasxspc linea9))
   (setq linea10 (comasxspc linea10))
)

(defun comasxspc (vlinea)
  (if (/= vlinea nil)
   (progn
    (setq x (substr vlinea 1 1))
    (setq cont 1)
    (setq vlinea2 "")
    (while (/= x "")
      (if (= x ",") (setq x "              "))
      (setq vlinea2 (strcat vlinea2 x))
      (setq cont (1+ cont))
      (setq x (substr vlinea cont 1))
    )
   )
  )
  (print vlinea2) 
)
