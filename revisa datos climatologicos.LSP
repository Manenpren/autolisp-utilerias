(defun segundop ()
  (setq LISTADCLOBJ "")
  (setq LISTADCLOBJ2 "")
  (C:LIBRERIA "ENTRADAS Y SALIDAS AL REGISTRO DE OBJETOS DCL2")
  (C:LIBRERIA "activa y desactiva objetos dcl")
  (C:LIBRERIA "dibuja objetos en pantalla")
  (C:LIBRERIA "BUSCA ACCION OBJETOS DIALOGO2")
  (C:LIBRERIA "intercambio excel")
  (C:LIBRERIA "lee datos estacion excel")
  (C:LIBRERIA "escribe texto img justif")
  (C:LIBRERIA "genera reportes")
  (C:LIBRERIA "lee datos estacion")
  (C:LIBRERIA "persistencia anderson")
  (C:LIBRERIA "prueba de secuencias")
  (C:LIBRERIA "test de helmert")
  (C:LIBRERIA "test mann kendall")
  (C:LIBRERIA "test cramer")
  (C:LIBRERIA "test student")
  (C:LIBRERIA "regresion lineal")
  (C:LIBRERIA "correlacionvarios")
  (C:LIBRERIA "genera reporte CORRELACION")
  (C:LIBRERIA "funcion grafica2")
  (C:LIBRERIA "fecha to fecha cadena")
  (C:LIBRERIA "ranges")
  (C:LIBRERIA "reportes")
  (C:LIBRERIA "return")
  (setq Xcolocaesta nil)
  (setq graf 0)
  (SETQ ANCHOGRFVAL 0)
  (SETQ FECHAINIGRF "")
  (limpiaest)
  (setq nestclicom (LENGTH esataciones3))
  ;(if (= nestclicom 0)(setq nestclicom 1))
  (dialogo2)
  (if (= opback "s")(regresap))
  
)

(defun limpiaest ()
  (setq nest 1);1	
  (setq nestfc (/ (strlen ESTACFINALC) 5))
  (setq nestfe (/ (strlen ESTACFINALE) 5))
  (setq xinicialmapa 100);144
  (setq yinicialmapa 35)
  (setq anchomapa 600);642
  (setq altomapa 540);580
  (setq GBMIN (list (- (car CENTROIDEC) DBUS) (- (cadr CENTROIDEC) DBUS)))
  (setq GBMAX (list (+ (car CENTROIDEC) DBUS) (+ (cadr CENTROIDEC) DBUS)))
  (setq GBMIN (UTM-GEO GBMIN (ATOI ZONAH)))
  (setq GBMAX (UTM-GEO GBMAX (ATOI ZONAH)))
  (SETQ XGMIN (CAR GBMIN))
  (SETQ YGMIN (CADR GBMIN))
  (SETQ XGMAX (CAR GBMAX))
  (SETQ YGMAX (CADR GBMAX))
  (SETQ CUEVER 1)
  (SETQ matrizprov NIL)
  (setq estaciones3 nil)
  (setq estaciones4 nil)
  (setq matrizporcentajc2 nil)
  (setq matrizporcentajE2 nil)
  (setq ESTACFINALC2 "")
  (setq ESTACFINALE2 "")
  (repeat nestfc
    (setq estaccf (substr estacfinalc (1+ (* (1- CUEVER) 5)) 5))
    (setq verpol (cdr (assoc (atoi estaccf) matrizporcentajc)))
    (setq CONCATENADO (cons cuever verpol))
    (setq matrizporcentajc2 (append matrizporcentajc2 (list CONCATENADO)))
    (setq verpol (cdr (assoc (atoi estaccf) estaciones)))
    (setq CONCATENADO (cons cuever verpol));-1
    (setq estaciones3 (append estaciones3 (list CONCATENADO)))
    (setq CONCATENADO (cons (1- cuever) verpol))
    (setq CONCATENADO (cons (1- cuever) (list (atof (cadr verpol)) (atof (caddr verpol)))))
    (setq matrizprov (append matrizprov (list CONCATENADO)))
    (SETQ CUEVER (1+ CUEVER))
  )
  (setq barra1 nestfc)
  (setq num nestfc)
  (IF (/= MATRIZPROV NIL)
    (SETQ MATRIZEST (TRFCOR matrizprov anchomapa altomapa XGMIN YGMIN XGMAX YGMAX xinicialmapa yinicialmapa))
    (SETQ MATRIZEST NIL)
  )
  (SETQ CUEVER 1)
  (SETQ matrizprov NIL)
  (repeat nestfe
    (setq estacEf (substr estacfinalE (1+ (* (1- CUEVER) 5)) 5))
    (setq verpol (cdr (assoc (abs (atoi estacEf)) matrizporcentajE)))
    (setq CONCATENADO (cons cuever verpol))
    (setq matrizporcentajE2 (append matrizporcentajE2 (list CONCATENADO)))
    (setq verpol (cdr (assoc (abs(atoi estacef)) estaciones2)))
    (setq CONCATENADO (cons cuever verpol));-1
    (setq estaciones4 (append estaciones4 (list CONCATENADO)))
    (setq CONCATENADO (cons (1- cuever) verpol))
    (setq CONCATENADO (cons (1- cuever) (list (atof (cadr verpol)) (atof (caddr verpol)))))
    (setq matrizprov (append matrizprov (list CONCATENADO)))
    (SETQ CUEVER (1+ CUEVER))
  )
  (setq barra2 nestfe)
  (setq num2 nestfe)
  (IF (/= MATRIZPROV NIL)
    (SETQ MATRIZEST2 (TRFCOR matrizprov anchomapa altomapa XGMIN YGMIN XGMAX YGMAX xinicialmapa yinicialmapa))
    (SETQ MATRIZEST2 NIL)
  )
  (IF (/= matrizd NIL)
    (SETQ MATRIZDIBU (TRFCOR matrizd anchomapa altomapa XGMIN YGMIN XGMAX YGMAX xinicialmapa yinicialmapa))
    (SETQ MATRIZDIBU NIL)
  )
  (setq num2 0) 
  (if (= eclicom "1")
    (progn
      (SETQ IDEST 1)
      (while idest
        (setq idest (cdr (assoc num2 MATRIZEST)))
        (setq num2 (1+ num2))
      )
    )
  )
  (setq num3 0) 
  (if (= eeric "1")
    (progn
      (SETQ IDEST 1)
      (while idest
        (setq idest (cdr (assoc num3 MATRIZEST2)))
        (setq num3 (1+ num3))
      )
    )
  )
  (if (/= num2 0) (setq num2 (1- num2)))
  (if (/= num3 0) (setq num3 (1- num3)))
  (setq ntest (+ num2 num3))
)

(defun dibujo2()
  (start_image "imagen")                     
  (setq vzoom 1)
  (fill_image xinicialmapa yinicialmapa (+ anchomapa 100) altomapa 0)
  (SETQ CUEVER 0)
  (setq verpol (cdr (assoc cuever MATRIZDIBU)))
  (WHILE VERPOL
    (SETQ VERPOL2 VERPOL)
    (SETQ CUEVER (1+ CUEVER))
    (setq verpol (cdr (assoc cuever MATRIZDIBU)))
    (IF (AND VERPOL (/= CUEVER 0))
      (PROGN
        (SETQ X1 (ATOI (RTOS (CAR VERPOL2) 2 0))) 
        (SETQ Y1 (ATOI (RTOS (CADR VERPOL2) 2 0)))
        (SETQ X2 (ATOI (RTOS (CAR VERPOL) 2 0))) 
        (SETQ Y2 (ATOI (RTOS (CADR VERPOL) 2 0)))
        (vector_image X1 Y1 X2 Y2 1)
      )
    )
  )
  (if (= barra1 nil) (setq barra1 1))
  (if (= barra2 nil) (setq barra2 1))
  (if (/= MATRIZEST nil)
   (progn
    (SETQ CUEVER 0)
    (setq verpol (cdr (assoc cuever MATRIZEST)))
    (setq verpolxxx (cadr (assoc (1+ cuever) estaciones3)))	
    (SETQ CONTANIM 1)
    (dos_waitcursor t)
    (dos_getprogress "Trabajando" "Dibujando estaciones" barra1)
    (WHILE VERPOL
      (SETQ X (ATOI (RTOS (CAR VERPOL) 2 0))) 
      (SETQ Y (ATOI (RTOS (CADR VERPOL) 2 0)))
      (slide_image (- X 20) (- Y 20) 40 40 (STRCAT RUTA "SLIDES\\eazul.SLD"))
      (if (< contanim barra1)
        (anim2) 
      )
      (stexto verpolxxx "romans" 18 (- X 20) (- Y 40))
      (SETQ CUEVER (1+ CUEVER))
      (setq verpol (cdr (assoc cuever MATRIZEST)))
      (setq verpolxxx (cadr (assoc (1+ cuever) estaciones3)))	
    )
    (dos_getprogress t)
    (dos_waitcursor)
   )
  )
  (if (/= MATRIZEST2 nil)
   (progn
    (SETQ CUEVER 0)
    (setq verpol (cdr (assoc cuever MATRIZEST2)))
    (setq verpolxxx (cadr (assoc (1+ cuever) estaciones4)))
    (SETQ CONTANIM 1)	
    (dos_waitcursor t)
    (dos_getprogress "Trabajando" "Dibujando estaciones" barra2)
    (WHILE VERPOL
      (SETQ X (ATOI (RTOS (CAR VERPOL) 2 0))) 
      (SETQ Y (ATOI (RTOS (CADR VERPOL) 2 0)))
      (slide_image (- X 25) (- Y 20) 40 40 (STRCAT RUTA "SLIDES\\eamari.sld"))
      (if (< contanim barra2)
        (anim2) 
      )
      (stexto verpolxxx "romans" 18 (- X 25) (+ Y 20))
      (SETQ CUEVER (1+ CUEVER))
      (setq verpol (cdr (assoc cuever MATRIZEST2)))
      (setq verpolxxx (cadr (assoc (1+ cuever) estaciones4)))	
    )
    (dos_getprogress t)
    (dos_waitcursor)
   )
  )
  (slide_image (+ xinicialmapa 560) (+ yinicialmapa 8) 80 97 (STRCAT RUTA "SLIDES\\MAPA2(NORTE).sld"))
  (slide_image (+ xinicialmapa 35) (+ yinicialmapa 521) 143 63 (STRCAT RUTA "SLIDES\\MAPA2(GENERAL).sld"))
  (slide_image (+ xinicialmapa 500) (+ yinicialmapa 521) 143 60 (STRCAT RUTA "SLIDES\\MAPA2(RESUMEN).sld"))
  (activa2 "MPRINCIPAL")
  (activa2 "DATOSF")
  (activa2 "mapa")
  (activa2 "SELEC")
  (dibujaptn)
  (slide_image 795 456 74 9 (STRCAT RUTA "SLIDES\\seleccionar.sld"))
  (end_image)
)

(defun dialogo2()
  (SETQ VARGRF2 "001190001011900010120000101200001011010001001")
;  (SETQ VARGRF2 "00119000101190001012000010120000101 1010001001")
  (setq estaciones2 estaciones4)
  (setq estaciones estaciones3)
  (setq dcl_id (load_dialog (strcat ruta "dialogos\\estaciones climatologicas.dcl"))) 
  (new_dialog "EST2" dcl_id)
  (DIBUJO2)
  (action_tile "estar" "(v92)")
  (action_tile "estab" "(V102)")
  (action_tile "cancel" "(exit)")
  (action_tile "imagen" "(picaste2 $x $y)")
  (action_tile "regreasaatras" "(cerrar)")
  (start_dialog)                          ; Display the dialog                                      ; box.
  (unload_dialog dcl_id)                  ; Unload the DCL file.
  (princ)
)

(defun cerrar ()
(setq opback "s")
(done_dialog dcl_id)
;(regresap)
  )

(defun regresap()
 ; (exit)
  ;(unload_dialog dcl_id)
  (C:LIBRERIA "UTM-GEO")
  (C:LIBRERIA "GEO-UTM")
  (C:LIBRERIA "encuentra zona horaria municipio")
  (C:LIBRERIA "CENTROIDE DE UN POLIGONO IRREGULAR2")
  (C:LIBRERIA "VERTICES TO BD POLYLINE")
  (C:LIBRERIA "BUSCA ESTACIONES CLIMATOLOGICAS CLICOM")
  (C:LIBRERIA "BUSCA ESTACIONES CLIMATOLOGICAS ERICK")
  (C:LIBRERIA "BUSCA ESTADO DE GEO")
  (C:LIBRERIA "tranforma coordenadas dibujo im")
  (C:LIBRERIA "escribe texto img")
  (C:LIBRERIA "acota grafica")
  (C:LIBRERIA "ENTRADAS Y SALIDAS AL REGISTRO DE OBJETOS DCL")
  (C:LIBRERIA "BUSCA ACCION OBJETOS DIALOGO")
  (C:LIBRERIA "descompacta cadena")
  (C:LIBRERIA "grafica parametro clima estacion")
  (C:LIBRERIA "controla grafica")
  (C:LIBRERIA "sector cuadricula")
  (C:LIBRERIA "muestra color")
  (C:LIBRERIA "numero de dias del mes fecha")
  (C:LIBRERIA "indice graficos fechas")
  (setq numeroindicef "01")
  (setq numeroindicet "001")
  (setq estaciones nil)
  (setq estaciones2 nil)
  (setq listadclobj "")
  (COMMAND "UNDO" "M")
  (setq contz 0)
  (setq procedencia "")
  (setq ESTACFINALC "")
  (setq ESTACFINALE "")
  (SETQ DIALOGOGRF "0116511052000000000")
  (setq colorgrf "007131141140142152154164166176178")
  (SETQ DATCLIMASOBRE "1")
  (LOAD (STRCAT RUTAFAS "ENCUENTRA ESTACIONES CLIMATICAS"))
  (setq xyz (list (car CENTROIDEC) (cadr CENTROIDEC)))
  (setq puntogeo (UTM-GEO xyz (ATOI ZONAH)))
  (SETQ CUEVER 0)
  (setq verpol (cdr (assoc cuever BDPOLI)))
  (SETQ XMIN (RTOS (car VERPOL) 2 5))
  (SETQ YMIN (RTOS (caDr VERPOL) 2 5))
  (SETQ XMAX (RTOS (car VERPOL) 2 5))
  (SETQ YMAX (RTOS (caDr VERPOL) 2 5))
  (SETQ matrizd NIL)
  (WHILE VERPOL
    (setq puntogeox (UTM-GEO (list (car verpol) (cadr verpol)) (ATOI ZONAH)))
    (setq CONCATENADOx (cons cuever puntogeox))
    (setq matrizd (append matrizd (list CONCATENADOx)))
    (SETQ XI (RTOS (car VERPOL) 2 5))
    (SETQ YI (RTOS (caDr VERPOL) 2 5))
    (IF (> XI XMAX)(SETQ XMAX XI))
    (IF (< XI XMIN)(SETQ XMIN XI))
    (IF (> YI YMAX)(SETQ YMAX YI))
    (IF (< YI YMIN)(SETQ YMIN YI))
    (SETQ CUEVER (1+ CUEVER))
    (setq verpol (cdr (assoc cuever BDPOLI)))
  )
  (if (> (abs (- (atof xmin) (atof xmax))) (abs (- (atof ymin) (atof ymax))))
    (setq dbus (fix (* 0.6 (abs (- (atof xmin) (atof xmax))))))
    (setq dbus (fix (* 0.6 (abs (- (atof ymin) (atof ymax))))))
  )
  (setq GBMIN (list (- (car CENTROIDEC) DBUS) (- (cadr CENTROIDEC) DBUS)))
  (setq GBMAX (list (+ (car CENTROIDEC) DBUS) (+ (cadr CENTROIDEC) DBUS)))
  (setq GBMIN (UTM-GEO GBMIN (ATOI ZONAH)))
  (setq GBMAX (UTM-GEO GBMAX (ATOI ZONAH)))
  (busca gbmin gbmax)
  (while (and (= estaciones nil) (= estaciones2 nil))
    (dos_splash (strcat ruta "ajuste.htj") 2)
    (setq dbus (* 1.4 dbus))
    (setq GBMIN (list (- (car CENTROIDEC) DBUS) (- (cadr CENTROIDEC) DBUS)))
    (setq GBMAX (list (+ (car CENTROIDEC) DBUS) (+ (cadr CENTROIDEC) DBUS)))
    (setq GBMIN (UTM-GEO GBMIN (ATOI ZONAH)))
    (setq GBMAX (UTM-GEO GBMAX (ATOI ZONAH)))
    (busca gbmin gbmax)
  )
   (SETQ LISTADCLOBJ (MBDDCL LISTADCLOBJ "B" 0 0 0 0 "DIBUJO"))
  (dialogox)
    (if (= opbusqueda "s") (segundop))
  (while (= opbusqueda "b")
    (setq GBMIN (list (- (car CENTROIDEC) DBUS) (- (cadr CENTROIDEC) DBUS)))
    (setq GBMAX (list (+ (car CENTROIDEC) DBUS) (+ (cadr CENTROIDEC) DBUS)))
    (setq GBMIN (UTM-GEO GBMIN (ATOI ZONAH)))
    (setq GBMAX (UTM-GEO GBMAX (ATOI ZONAH)))
    (busca gbmin gbmax)
    (while (and (= estaciones nil) (= estaciones2 nil))
      (dos_splash (strcat ruta "ajuste.htj") 2)
      (setq dbus (* 1.4 dbus))
      (setq GBMIN (list (- (car CENTROIDEC) DBUS) (- (cadr CENTROIDEC) DBUS)))
      (setq GBMAX (list (+ (car CENTROIDEC) DBUS) (+ (cadr CENTROIDEC) DBUS)))
      (setq GBMIN (UTM-GEO GBMIN (ATOI ZONAH)))
      (setq GBMAX (UTM-GEO GBMAX (ATOI ZONAH)))
      (busca gbmin gbmax)
    );while
    (dialogox)
  )
  (load (strcat RUTAFAS "revisa datos climatologicos"))
  (segundop)
;;  (regresapp)
 )
 
(defun picaste2 (x y)
  (start_image "imagen")
  (setq xesta x)
  (setq yesta y)
  (if (or (= mouser nil) (/= mouser mouse)) (setq mouser mouse))
  (if (or (= mouse2r nil) (/= mouse2r mouse2)) (setq mouse2r mouse2))
  (SETQ MOUSE (BUSACC2 LISTADCLOBJ X Y 74))
  (SETQ MOUSE2 (BUSACC2 LISTADCLOBJ2 X Y 274))
  ;;_Promedios Moviles
  (if (and (< xesta 150) (> xesta 140) (< yesta 25))
    (progn
      (if (> yesta 20)
	(progn
	  (setq cadena (leeconcentrado (estacion procedencia)))

	)
       )
      )
    )
  ;;_Termina PMov
  (IF (= MOUSE "SEL1")
    (progn
      (if (= (estdefinitiva2 nest) "S")
        (progn
          (estdefinitivab2 nest)
        )
        (progn
          (if (> nest num2)
            (setq ESTACFINALE2 (strcat ESTACFINALE2 (ntocad nest 0 5)))
            (setq ESTACFINALC2 (strcat ESTACFINALC2 (ntocad nest 0 5)))
          )
        )
      )
    )
  )
  (if (= mouse "CORRELACIONOBJ")
    (progn
      (setq colorgrf (seccuad matrizcorrelaf (* nestactbl anchocuad 1.0000) (* nestactbl anchocuad 1.0000) nestactbl nestactbl 152 9 x y))
      (start_image "imagen") 
      (fill_image 279 522 69 18 252)
      (fill_image 279 548 128 18 252)
      (stextoj (strcat (substr colorgrf 1 6) "-" (substr colorgrf 7 6)) "romans" 15 280 549 "A")
      (stextoj (substr colorgrf 13 8) "romans" 15 282 523 "A")
      (end_image)
    )
  );if
  (if (= MOUSE "DIBUJO")
    (progn
      (SETQ OBJETO (BUSOBJBD LISTADCLOBJ 74 MOUSE));74??
      (setq statusobj (SUBSTR OBJETO 32 1))
      (IF (= statusobj "0")
       (PROGN
        (setq kx x)
        (setq ky y)
        (DESTA2 vzoom) 
        (setq x kx)
        (setq y ky)
        (setq dstx 1000000)
        (setq num22x 0)
        (if (/= MATRIZEST nil)
          (progn
            (SETQ IDESTx 1)
            (setq idestx (cdr (assoc num22x MATRIZEST)))
            (while idestx
              (SETQ pX (ATOI (RTOS (CAR idestx) 2 0)))
              (SETQ pY (ATOI (RTOS (CADR idestx) 2 0)))
              (setq distxc (distance (list x y) (list px py)))
              (if (< distxc dstx) 
  	      (progn
                  (setq dstx distxc)
                  (setq nestc (1+ num22x))
                );progn      
              );if
              (setq num22x (1+ num22x))
              (setq idestx (cdr (assoc num22x MATRIZEST)))
            );while
          );progn
        );if
        (setq distxc dstx)
        (setq num3x 0) 
        (if (/= MATRIZEST2 nil)
          (progn
            (SETQ IDESTx 1)
            (setq idestx (cdr (assoc num3x MATRIZEST2)))
            (while idestx
              (SETQ pX (ATOI (RTOS (CAR idestx) 2 0)))
              (SETQ pY (ATOI (RTOS (CADR idestx) 2 0)))
              (setq distxe (distance (list x y) (list (- px 5) py)))
              (if (< distxe dstx)  
	      (progn  
                 (set q dstx distxe)
                 (setq neste (1+ num3x ));num2+
               );progn      
             );if  
             (setq num3x (1+ num3x))
             (setq idestx (cdr (assoc num3x MATRIZEST2)))
           );while    
         );progn
       );if
       (setq distxe dstx)
       (if (< distxe distxc) (setq nest (+ neste nestfc))(setq nest nestc))
       (dpuntero2 vzoom)
      )
     )
    )
  );progn
  (IF (= MOUSE "SALIR11");;//correlacion/modifique
    (PROGN
      (dibuja3)
      (setq graf 0)
      (activa3 "PR1")
      (activa3 "PR2")
      (activa3 "PR3")
      (activa3 "DATOSF1")
      (activa3 "DATOSF2")
      (activa3 "DATOSF3")
      (activa3 "DATOSF4")
      (activa3 "DATOSF5")
      (activa2 "mapa")
      (activa3 "SEL1")
      (DESactiva2 "CREPORTE2")
    )
  )
  (IF (= MOUSE "SALIRC1")
    (PROGN
      (dibuja3)
      (setq graf 0)
      (activa3 "PR1")
      (activa3 "PR2")
      (activa3 "PR3")
      (activa3 "DATOSF1")
      (activa3 "DATOSF2")
      (activa3 "DATOSF3")
      (activa3 "DATOSF4")
      (activa3 "DATOSF5")
      (activa2 "mapa")
      (activa3 "SEL1")
      (DESactiva2 "CORREPORTE")
     ; (SETQ LISTADCLOBJ (MBDDCL2 LISTADCLOBJ "B" 0 0 0 0 "MATRIZCORRELA" "A" "0" "" "" "" "" "0" "0" ""))
      (DESactiva2 "LLENA")
       ;(activa2 "LLENA")
       (dibujaelem (BUSOBJBD LISTADCLOBJ2 274 "LLENA1"))
       (dibujaelem (BUSOBJBD LISTADCLOBJ2 274 "LLENA2"))
       (dibujaelem (BUSOBJBD LISTADCLOBJ 74 "LLENAEJE1"))
       (dibujaelem (BUSOBJBD LISTADCLOBJ 74 "LLENAEJE2"))
      (SETQ LISTADCLOBJ (MBDDCL2 LISTADCLOBJ "B" 152 9 (+ 152 (* ANCHOCUAD nestactbl)) (+ 9 (* ANCHOCUAD nestactbl)) "CORRELACIONOBJ" "X" "0" "x" "x" "x" "" "0" "0" ""))
     ;  (SETQ LISTADCLOBJ (MBDDCL2 LISTADCLOBJ "B" 0 0 0 0 "DIBUJO" "A" "0" "" "" "" "" "0" "0" ""))
    )
  )
  (IF (= MOUSE "EXCELC1");Reporte correlacion
  ; (progn
    (greportecorrel resultadocorr)
    ;(greportC resultadocorr)
  ; )
  )  
    
  (IF (= MOUSE "CONSEJE1")
    (PROGN
      (SETQ DATOSFT1 (investigobj "DATOSF1"))
      (SETQ DATOSFT2 (investigobj "DATOSF2"))
      (SETQ DATOSFT3 (investigobj "DATOSF3"))
      (SETQ DATOSFT5 (investigobj "DATOSF5"))
      (SETQ consiste (investigobj "CONSIST1"))
      (IF (AND (/= DATOSFT1 NIL) (/= DATOSFT2 NIL) (/= DATOSFT3 NIL) (/= consiste NIL))
        (PROGN
          (setq verpolxxx(nestacc3 nest))
          (greport (+ 2 consiste) (CAR VERPOLXXX) (SUBSTR procedencia 1 1) DATOSFT2 DATOSFT1 DATOSFT3)
        );progn
        (ALERT "DATOS INCOMPLETOS NO SE PUEDE GENERAR REPORTE")
      )
    )
  )
  (IF (= MOUSE "LLENAEJE2")
    (PROGN
      (SETQ DATOSFT1 (investigobj "DATOSF1"))
      (SETQ DATOSFT2 (investigobj "DATOSF2"))
      (SETQ DATOSFT3 (investigobj "DATOSF3"))
      (SETQ DATOSFT5 (investigobj "DATOSF5"))
      (SETQ consiste (investigobj "LLENA2"))
      (IF (AND (/= DATOSFT1 NIL) (/= DATOSFT2 NIL) (/= DATOSFT3 NIL) (/= consiste NIL))
        (if (= consiste 3)
          (PROGN
            (if (= DATOSFT5 2)
              (progn
                (setq nciclosx (/ (strlen ESTACFINALC2) 5))
                (setq nciclosx2 (/ (strlen ESTACFINALE2) 5))
                (setq contcic 1)
                (setq listacorr "")
                (repeat (+ nciclosx nciclosx2)
                  (if (<= contcic nciclosx)
                    (setq estacproc (substr ESTACFINALC2 (1+ (* 5 (1- contcic))) 5))
                    (setq estacproc (substr ESTACFINALE2 (1+ (* 5 (- contcic nciclosx 1))) 5))
                  )
                  (setq verpolxxx (nestacc3 (atoi estacproc)))
                  (if (and (/= verpolxxx nil) (/= verpolxxx "no"))
                    (setq listacorr (strcat listacorr (CAR VERPOLXXX) (SUBSTR procedencia 1 1)))
                  )
                  (setq contcic (1+ contcic))
                );repeat
               )
            );if
            (if (= DATOSFT5 3)
              (progn
                (setq contcic 1)
                (setq verpolxxx (nestacc3 contcic))
                (setq listacorr "")
                (while (/= verpolxxx "no")
                  (setq listacorr (strcat listacorr (CAR VERPOLXXX) (SUBSTR procedencia 1 1)))
                  (setq contcic (1+ contcic))
                  (setq verpolxxx (nestacc3 contcic))
                 );while
              )
            );if
            (if (OR (= DATOSFT5 3) (= DATOSFT5 2))
              (PROGN
                (setq resultadocorr (correlacionv listacorr "C" DATOSFT2 "19000101" DATOSFT1 DATOSFT3))
                (greportc resultadocorr)
              )
            )
          );progn    
        )
        (ALERT "DATOS INCOMPLETOS NO SE PUEDE GENERAR REPORTE")
      )
    )
  )
  (IF (= MOUSE "CONSEJE2")
    (PROGN
      (SETQ DATOSFT1 (investigobj "DATOSF1"))
      (SETQ DATOSFT2 (investigobj "DATOSF2"))
      (SETQ DATOSFT3 (investigobj "DATOSF3"))
      (SETQ DATOSFT5 (investigobj "DATOSF5"))
      (SETQ consiste (investigobj "CONSIST2"))
      (IF (AND (/= DATOSFT1 NIL) (/= DATOSFT2 NIL) (/= DATOSFT3 NIL) (/= consiste NIL))
        (PROGN
          (setq verpolxxx (nestacc3 nest))
          (greport (+ 5 consiste) (CAR VERPOLXXX) (SUBSTR procedencia 1 1) DATOSFT2 DATOSFT1 DATOSFT3)
        );progn
        (ALERT "DATOS INCOMPLETOS NO SE PUEDE GENERAR REPORTE")
      )
    )
  )
  (IF (= (SUBSTR MOUSE 1 3) "ACC")
    (PROGN
      (SETQ OBJETO (BUSOBJBD LISTADCLOBJ 74 MOUSE))
      (setq statusobj (SUBSTR OBJETO 32 1))
      (IF (= statusobj "0")
         (DESPULSA3 "CONSEJE2")
      ) 
      (IF (= statusobj "1")
        (progn  
        (IF (= MOUSE "ACC13")
          (PROGN
            (DESPULSA3 MOUSE)
	    (setq graf 0)
            (fill_image 0 0 773 624 0)
            (fill_image 774 450 141 118 0)
            (activa3 "PR1")
            (activa3 "PR2")
            (activa3 "PR3")
            (activa3 "PR4")
            (activa2 "mapa")
            (activa3 "SEL1")
            (desactiva2 "TOOLSGRF")
            (DESACTIVA "INDICES")
            (desactiva2 "colorgrf1")
            (desactiva2 "colorgrf2")
            (desactiva2 "rcmobj")
            (desactiva2 "rctobj")
            (desactiva2 "vmobj")
            (desactiva2 "vmiobj")
            (desactiva2 "vmeobj")
            (desactiva2 "sumobj")
            (desactiva2 "sobobj")
            (dibujaelem (BUSOBJBD LISTADCLOBJ 74 "PR1"))
            (dibujaelem (BUSOBJBD LISTADCLOBJ 74 "PR2"))
            (dibujaelem (BUSOBJBD LISTADCLOBJ 74 "PR3"))
            (dibujaelem (BUSOBJBD LISTADCLOBJ 74 "PR4"))
            (DIBUJO2)
          )
        )
        (IF (OR (= MOUSE "ACC03") (= MOUSE "ACC04") (= MOUSE "ACC05"))
	  (progn
          (DESPULSA2 MOUSE)
	  (actualizagraf2)
	  )
        )
        (IF (OR (= MOUSE "ACC01") (= MOUSE "ACC02") (= MOUSE "ACC06") (= MOUSE "ACC07") (= MOUSE "ACC08") (= MOUSE "ACC09") (= MOUSE "ACC10") (= MOUSE "ACC11") (= MOUSE "ACC14"))
          (progn
            (DESPULSA3 MOUSE)
            (if (= MOUSE "ACC01")
              (progn
                (fill_image 414 381 361 243 31)
                (fill_image 414 381 175 20 105)
                (slide_image 419 406 164 186 (STRCAT RUTA "SLIDES\\colores.SLD"))
                (slide_image 414 381 175 216 (STRCAT RUTA "SLIDES\\coloresx.SLD"))
                (activa2 "colorgrf1")
              )
            )
            (if (= MOUSE "ACC02")
              (progn
                (fill_image 414 381 361 243 31)
                (fill_image 414 381 175 20 105)
                (slide_image 422 409 158 118 (STRCAT RUTA "SLIDES\\colores2.SLD"))
                (slide_image 422 529 72 47 (STRCAT RUTA "SLIDES\\colores3.SLD"))
                (slide_image 414 381 175 216 (STRCAT RUTA "SLIDES\\coloresx.SLD"))
                (activa2 "colorgrf2")
              )
            )
            (if (= MOUSE "ACC06")
              (progn
                (fill_image 414 381 360 243 252)
                (fill_image 414 381 360 20 105)
                (fill_image 414 473 360 20 105)
                (fill_image 422 433 95 15 250)
                (fill_image 422 453 95 15 250)
                (fill_image 601 433 95 15 250)
                (fill_image 601 453 95 15 250)
                (slide_image 414 381 360 243 (STRCAT RUTA "SLIDES\\CMBSmED.sld"))
                (activa2 "rcmobj")
                (dibujaelem (BUSOBJBD LISTADCLOBJ 74 "RCM01"))
                (dibujaelem (BUSOBJBD LISTADCLOBJ 74 "RCM02"))
                (dibujaelem (BUSOBJBD LISTADCLOBJ 74 "RCM03"))
                (dibujaelem (BUSOBJBD LISTADCLOBJ 74 "RCM04"))
                (dibujaelem (BUSOBJBD LISTADCLOBJ 74 "RCM05"))
                (dibujaelem (BUSOBJBD LISTADCLOBJ 74 "RCM06"))
                (dibujaelem (BUSOBJBD LISTADCLOBJ 74 "RCM07"))
                (dibujaelem (BUSOBJBD LISTADCLOBJ 74 "RCM08"))
                (dibujaelem (BUSOBJBD LISTADCLOBJ 74 "RCM09"))
                (dibujaelem (BUSOBJBD LISTADCLOBJ 74 "RCM10"))
                (dibujaelem (BUSOBJBD LISTADCLOBJ 74 "RCM11"))
                (dibujaelem (BUSOBJBD LISTADCLOBJ 74 "RCM12"))
                (dibujaelem (BUSOBJBD LISTADCLOBJ 74 "RCM12"))
                (dibujaelem (BUSOBJBD LISTADCLOBJ 74 "EJEGRF1"))
                (SETQ FECHAINIX (ftofcad (substr vargrf2 4 8)))
                (SETQ FECHAFINX (ftofcad (substr vargrf2 12 8)))
                (stextoj FECHAINIX "romans" 12 430 447 "C")
                (stextoj FECHAFINX "romans" 12 430 467 "C")
                (SETQ FECHAINIX (ftofcad (substr vargrf2 20 8)))
                (SETQ FECHAFINX (ftofcad (substr vargrf2 28 8)))
                (stextoj FECHAINIX "romans" 12 610 447 "C")
                (stextoj FECHAFINX "romans" 12 610 467 "C")
              )
            )
            (if (= MOUSE "ACC07")
              (progn
                (fill_image 414 381 360 243 252)
                (fill_image 414 381 360 20 105)
                (fill_image 414 450 360 20 105)
                (fill_image 505 411 115 15 250)
                (fill_image 505 431 115 15 250)
                (slide_image 414 381 360 243 (STRCAT RUTA "SLIDES\\CMBStEnD.sld"))
                (activa2 "rctobj")
                (dibujaelem (BUSOBJBD LISTADCLOBJ 74 "RCT01"))
                (dibujaelem (BUSOBJBD LISTADCLOBJ 74 "RCT02"))
                (dibujaelem (BUSOBJBD LISTADCLOBJ 74 "RCT03"))
                (dibujaelem (BUSOBJBD LISTADCLOBJ 74 "RCT04"))
                (dibujaelem (BUSOBJBD LISTADCLOBJ 74 "RCT05"))
                (dibujaelem (BUSOBJBD LISTADCLOBJ 74 "RCT06"))
                (dibujaelem (BUSOBJBD LISTADCLOBJ 74 "EJEGRFC"))
                (SETQ FECHAINIX (ftofcad (substr vargrf2 4 8)))
                (SETQ FECHAFINX (ftofcad (substr vargrf2 12 8)))
                (stextoj FECHAINIX "romans" 12 510 424 "C")
                (stextoj FECHAFINX "romans" 12 510 445 "C")
              )
            )
            (if (= MOUSE "ACC08")
              (progn
                (fill_image 414 381 360 243 31)
                (fill_image 414 381 360 20 105)
                (fill_image 505 410 115 15 252)
                (fill_image 505 431 115 15 252)
                (fill_image 461 458 115 15 252)
                (slide_image 414 381 360 243 (STRCAT RUTA "SLIDES\\CMBSvMAX.sld"))
                (activa2 "vmobj")
                (dibujaelem (BUSOBJBD LISTADCLOBJ 74 "VM01"))
                (dibujaelem (BUSOBJBD LISTADCLOBJ 74 "VM02"))
                (dibujaelem (BUSOBJBD LISTADCLOBJ 74 "VM03"))
                (dibujaelem (BUSOBJBD LISTADCLOBJ 74 "VM04"))
                (dibujaelem (BUSOBJBD LISTADCLOBJ 74 "VM05"))
                (dibujaelem (BUSOBJBD LISTADCLOBJ 74 "VM06"))
                (dibujaelem (BUSOBJBD LISTADCLOBJ 74 "EJEGRFV"))
                (SETQ FECHAINIX (ftofcad (substr vargrf2 4 8)))
                (SETQ FECHAFINX (ftofcad (substr vargrf2 12 8)))
                (stextoj FECHAINIX "romans" 12 510 424 "C")
                (stextoj FECHAFINX "romans" 12 510 445 "C")
              )
            )
            (if (= MOUSE "ACC09")
              (progn
                (fill_image 414 381 360 243 31)
                (fill_image 414 381 360 20 105)
                (fill_image 505 410 115 15 252)
                (fill_image 505 431 115 15 252)
                (fill_image 461 458 115 15 252)
                (slide_image 414 381 360 243 (STRCAT RUTA "SLIDES\\CMBSvMIN.sld"))
                (activa2 "vmiobj")
                (dibujaelem (BUSOBJBD LISTADCLOBJ 74 "VMI01"))
                (dibujaelem (BUSOBJBD LISTADCLOBJ 74 "VMI02"))
                (dibujaelem (BUSOBJBD LISTADCLOBJ 74 "VMI03"))
                (dibujaelem (BUSOBJBD LISTADCLOBJ 74 "VMI04"))
                (dibujaelem (BUSOBJBD LISTADCLOBJ 74 "VMI05"))
                (dibujaelem (BUSOBJBD LISTADCLOBJ 74 "VMI06"))
                (dibujaelem (BUSOBJBD LISTADCLOBJ 74 "EJEGRFI"))
                (SETQ FECHAINIX (ftofcad (substr vargrf2 4 8)))
                (SETQ FECHAFINX (ftofcad (substr vargrf2 12 8)))
                (stextoj FECHAINIX "romans" 12 510 424 "C")
                (stextoj FECHAFINX "romans" 12 510 445 "C")
              )
            )
            (if (= MOUSE "ACC10")
              (progn
                (fill_image 414 381 360 243 31)
                (fill_image 414 381 360 20 105)
                (fill_image 505 410 115 15 252)
                (fill_image 505 431 115 15 252)
                (fill_image 461 458 115 15 252)
                (slide_image 414 381 360 243 (STRCAT RUTA "SLIDES\\CMBSvMED.sld"))
                (activa2 "vmeobj")
                (dibujaelem (BUSOBJBD LISTADCLOBJ 74 "VME011"))
                (dibujaelem (BUSOBJBD LISTADCLOBJ 74 "VME021"))
                (dibujaelem (BUSOBJBD LISTADCLOBJ 74 "VME031"))
                (dibujaelem (BUSOBJBD LISTADCLOBJ 74 "VME041"))
                (dibujaelem (BUSOBJBD LISTADCLOBJ 74 "VME051"))
                (dibujaelem (BUSOBJBD LISTADCLOBJ 74 "VME061"))
                (dibujaelem (BUSOBJBD LISTADCLOBJ 74 "EJEGRFE"))
                (SETQ FECHAINIX (ftofcad (substr vargrf2 4 8)))
                (SETQ FECHAFINX (ftofcad (substr vargrf2 12 8)))
                (stextoj FECHAINIX "romans" 12 510 424 "C")
                (stextoj FECHAFINX "romans" 12 510 445 "C")
              );progn
            );if
            (if (= MOUSE "ACC11")
              (progn
                (fill_image 414 381 360 243 31)
                (fill_image 414 381 360 20 105)
                (fill_image 505 410 115 15 252)
                (fill_image 505 431 115 15 252)
                (fill_image 461 458 115 15 252)
                (slide_image 414 381 360 243 (STRCAT RUTA "SLIDES\\CMBSvSUM.sld"))
                (activa2 "sumobj")
                (dibujaelem (BUSOBJBD LISTADCLOBJ 74 "SUM01"))
                (dibujaelem (BUSOBJBD LISTADCLOBJ 74 "SUM02"))
                (dibujaelem (BUSOBJBD LISTADCLOBJ 74 "SUM03"))
                (dibujaelem (BUSOBJBD LISTADCLOBJ 74 "SUM04"))
                (dibujaelem (BUSOBJBD LISTADCLOBJ 74 "SUM05"))
                (dibujaelem (BUSOBJBD LISTADCLOBJ 74 "SUM06"))
                (dibujaelem (BUSOBJBD LISTADCLOBJ 74 "EJEGRFS"))
                (SETQ FECHAINIX (ftofcad (substr vargrf2 4 8)))
                (SETQ FECHAFINX (ftofcad (substr vargrf2 12 8)))
                (stextoj FECHAINIX "romans" 12 510 424 "C")
                (stextoj FECHAFINX "romans" 12 510 445 "C")
              );progn
            );if
            (if (= MOUSE "ACC14")
              (progn
                (fill_image 414 381 360 243 31)
                (fill_image 414 381 360 20 105)
                (fill_image 432 417 76 52 252)
                (fill_image 512 417 76 52 252)
                (fill_image 432 480 76 52 252)
                (fill_image 512 480 76 52 252)
                (fill_image 592 480 76 52 252)
                (fill_image 672 480 76 52 252)
                (fill_image 432 543 76 52 252)
                (fill_image 512 543 76 52 252)
                (fill_image 592 543 76 52 252)
                (slide_image 414 381 360 243 (STRCAT RUTA "SLIDES\\CMBSsOBR.sld"))
                (slide_image 432 417 156 52 (STRCAT RUTA "SLIDES\\SBR1.sld"))
                (slide_image 432 480 316 52 (STRCAT RUTA "SLIDES\\SBR2.sld"))
                (slide_image 432 543 236 52 (STRCAT RUTA "SLIDES\\SBR3.sld"))
                (activa2 "sobobj")
                (SETQ L1ST (substr vargrf2 36 2))
                (SETQ L2ST (substr vargrf2 38 4))
                (SETQ L3ST (substr vargrf2 42 3))
                (SETQ OBJETO (BUSOBJBD LISTADCLOBJ2 274 "SOBRE1"))
                (setq LINEAFIN (strcat (substr OBJETO 1 254) L1ST (substr OBJETO 257)))
                (SETQ LISTADCLOBJ2 (ACTUALIZABD LISTADCLOBJ2 274 "SOBRE1" LINEAFIN))
                (SETQ OBJETO (BUSOBJBD LISTADCLOBJ2 274 "SOBRE2"))
                (setq LINEAFIN (strcat (substr OBJETO 1 254) L2ST (substr OBJETO 259)))
                (SETQ LISTADCLOBJ2 (ACTUALIZABD LISTADCLOBJ2 274 "SOBRE2" LINEAFIN))
                (SETQ OBJETO (BUSOBJBD LISTADCLOBJ2 274 "SOBRE3"))
                (setq LINEAFIN (strcat (substr OBJETO 1 254) L3ST (substr OBJETO 258)))
                (SETQ LISTADCLOBJ2 (ACTUALIZABD LISTADCLOBJ2 274 "SOBRE3" LINEAFIN))
                (dibujaelem (BUSOBJBD LISTADCLOBJ2 274 "SOBRE1"))
                (dibujaelem (BUSOBJBD LISTADCLOBJ2 274 "SOBRE2"))
                (dibujaelem (BUSOBJBD LISTADCLOBJ2 274 "SOBRE3"))
              );progn
            );if
          )
        );progn
        )
      )
    )
  )
  (if (= MOUSE "ACC12")
    (progn
      (DESPULSA3 MOUSE)
      (fill_image 0 0 773 624 252)
      (fill_image 591 52 171 20 105)
      (setq slidexx "BTNGRF(GRF)")
      (slide_image 0 0 761 381 (STRCAT RUTA "SLIDES\\" slidexx ".SLD"))
      (fill_image 0 381 166 17 105)
      (setq slidexx "BTNGRF(indice)")
      (slide_image 0 381 166 238 (STRCAT RUTA "SLIDES\\" slidexx ".SLD"))
      (fill_image 166 381 248 20 105)
      (setq slidexx "BTNGRF(datosg)")
      (slide_image 166 381 248 243 (STRCAT RUTA "SLIDES\\" slidexx ".SLD"))
      (setq slidexx "BTNGRF(datosg)")
      (slide_image 166 381 248 243 (STRCAT RUTA "SLIDES\\" slidexx ".SLD"))
      (dibujaelem (BUSOBJBD LISTADCLOBJ 74 "ACC14"))
      (dibujaelem (BUSOBJBD LISTADCLOBJ 74 "ACC01"))
      (dibujaelem (BUSOBJBD LISTADCLOBJ 74 "ACC02"))
      (dibujaelem (BUSOBJBD LISTADCLOBJ 74 "ACC03"))
      (dibujaelem (BUSOBJBD LISTADCLOBJ 74 "ACC04"))
      (dibujaelem (BUSOBJBD LISTADCLOBJ 74 "ACC05"))
      (dibujaelem (BUSOBJBD LISTADCLOBJ 74 "ACC06"))
      (dibujaelem (BUSOBJBD LISTADCLOBJ 74 "ACC07"))
      (dibujaelem (BUSOBJBD LISTADCLOBJ 74 "ACC08"))
      (dibujaelem (BUSOBJBD LISTADCLOBJ 74 "ACC09"))
      (dibujaelem (BUSOBJBD LISTADCLOBJ 74 "ACC10"))
      (dibujaelem (BUSOBJBD LISTADCLOBJ 74 "ACC11"))
      (dibujaelem (BUSOBJBD LISTADCLOBJ 74 "ACC12"))
      (dibujaelem (BUSOBJBD LISTADCLOBJ 74 "ACC13"))
      (dibujaelem (BUSOBJBD LISTADCLOBJ 74 "INDIR"))
      (dibujaelem (BUSOBJBD LISTADCLOBJ2 274 "DATOSF6"))
      (actualizagraf2)
      (rangosest)
      (setq colorxh (substr vargrf2 1 3))
      (muestracl colorxh 373 584 36 36)
      (dibujarect 370 581 411 622 20)
      (stexto ESTACION "romans" 20 342 412)
      (stexto (nombreestado) "romans" 20 170 412) 
      (stexto (denominacion) "romans" 20 170 448)
      
    )
  )  
  (IF (= (SUBSTR MOUSE 1 2) "CL")
    (PROGN
       (if (= mouse "CL1")
         (progn
           (setq colorgrf (seccuad "001002003004005006007008009010011012013014015016017018019020021022023024025026027028029030031032033034035036037038039040041042043044045046047048049050051052053054055056057058059060061062063064065066067068069070071072073074075076077078079080081082083084085086087088089090091092093094095096097098099100101102103104105106107108109110111112113114115116117118119120121122123124125126127128129130131132133134135136137138139140141142143144145146147148149150151152153154155156157158159160161162163164165166167168169170171172173174175176177178179180181182183184185186187188189190191192193194195196197198199200201202203204205206207208209210211212213214215216217218219220221222223224225226227228229230231232233234235236237238239240241242243244245246247248249250251252253254255" 164.000 186.000 15 17 419 406 x y))
           (setq VARGRF2 (strcat colorgrf (substr vargrf2 4)))
           (muestracl colorgrf 373 584 36 36)
           (dibujarect 370 581 411 622 20)
         )
       );if
       (if (= mouse "CL2")
         (progn
           (setq colorx (seccuad "256257258259260261262263264265266267268269270271272273274275276277278279280281282283284285286287288289290291292293294295296297298299300301302303304305" 158.000 118.000 5 10 422 409 x y))
           (setq VARGRF2 (strcat colorx (substr vargrf2 4)))
           (setq colorgrf (corrigecl colorx))
           (muestracl colorgrf 373 584 36 36)
           (dibujarect 370 581 411 622 20)
         )
       );if
       (if (= mouse "CL3")
         (progn
           (setq colorx (seccuad "306307308309" 72.000 47.000 1 4 422 529 x y))
           (setq VARGRF2 (strcat colorx (substr vargrf2 4)))
           (setq colorgrf (corrigecl colorx))
           (muestracl colorgrf 373 584 36 36)
           (dibujarect 370 581 411 622 20)
         )
       );if
    )
  )
  (IF (= MOUSE "RESUMEJE1")
    (PROGN
      (SETQ DATOSFT1 (investigobj "DATOSF1"))
      (SETQ DATOSFT2 (investigobj "DATOSF2"))
      (SETQ DATOSFT3 (investigobj "DATOSF3"))
      (SETQ DATOSFT5 (investigobj "DATOSF5"))
      (SETQ RESUMV (investigobj "RESUM1"))
      (IF (AND (/= DATOSFT1 NIL) (/= DATOSFT2 NIL) (/= DATOSFT3 NIL) (/= DATOSFT5 NIL) (/= RESUMV NIL))
        (PROGN
          (if (= DATOSFT5 1)
            (progn
              (setq verpolxxx (nestacc3 nest))
              (IF (= RESUMV 1) 
                (Lista->Excel (leebdex (CAR VERPOLXXX) (SUBSTR procedencia 1 1) DATOSFT2 DATOSFT1 DATOSFT3))
              )
              (IF (= RESUMV 2) 
                (Lista	->Excel (leebdex (CAR VERPOLXXX) (SUBSTR procedencia 1 1) DATOSFT2 DATOSFT1 "VC"))
              )
              (IF (>= RESUMV 3) 
                (greport RESUMV (CAR VERPOLXXX) (SUBSTR procedencia 1 1) DATOSFT2 DATOSFT1 DATOSFT3)
              )
            )
          )
          (if (= DATOSFT5 2)
            (progn
              (setq nciclosx (/ (strlen ESTACFINALC2) 5))
              (setq nciclosx2 (/ (strlen ESTACFINALE2) 5))
              (setq contcic 1)
              (repeat (+ nciclosx nciclosx2)
                (if (<= contcic nciclosx)
                  (setq estacproc (substr ESTACFINALC2 (1+ (* 5 (1- contcic))) 5))
                  (setq estacproc (substr ESTACFINALE2 (1+ (* 5 (- contcic nciclosx 1))) 5))
                )
                (setq verpolxxx (nestacc3 (atoi estacproc)))
                (IF (= RESUMV 1) 
                  (Lista->Excel (leebdex (CAR VERPOLXXX) (SUBSTR procedencia 1 1) DATOSFT2 DATOSFT1 DATOSFT3))
                )
                (IF (= RESUMV 2) 
                  (Lista->Excel (leebdex (CAR VERPOLXXX) (SUBSTR procedencia 1 1) DATOSFT2 DATOSFT1 "VC"))
                )
                (setq contcic (1+ contcic))
              );repeat
            )
          );if
          (if (= DATOSFT5 3)
            (progn
              (setq contcic 1)
              (setq verpolxxx (nestacc3 contcic))
              (while (/= verpolxxx "no")
                (IF (= RESUMV 1) 
                  (Lista->Excel (leebdex (CAR VERPOLXXX) (SUBSTR procedencia 1 1) DATOSFT2 DATOSFT1 DATOSFT3))
                )
                (IF (= RESUMV 2) 
                  (Lista->Excel (leebdex (CAR VERPOLXXX) (SUBSTR procedencia 1 1) DATOSFT2 DATOSFT1 "VC"))
                )
                (setq contcic (1+ contcic))
                (setq verpolxxx (nestacc3 contcic))
              );while
            )
          );if
        );progn
        (ALERT "DATOS INCOMPLETOS NO SE PUEDE GENERAR REPORTE")
      )
    )
  )
  (IF (OR (= MOUSE "PR1") (= MOUSE "PR2") (= MOUSE "PR3") (= MOUSE "PR4"))
    (PROGN
      (SETQ OBJETO (BUSOBJBD LISTADCLOBJ 74 MOUSE))
      (setq statusobj (SUBSTR OBJETO 32 1))
      (IF (= statusobj "0") 
        (PROGN
          (IF (= MOUSE "PR1") 
            (PROGN
              (DESactiva2 "CONSISTENCIA")
              (fill_image 0 0 144 257 0)
            )
          )
          (IF (= MOUSE "PR4") 
            (PROGN
	      ;(dialogoreg)
              (DESactiva2 "RESUMEN")
               (fill_image 0 0 144 235 0)
            )
          )
          (IF (= MOUSE "PR2") 
            (PROGN
              (DESactiva2 "LLENA")
               (fill_image 0 0 144 265 0)
            )
          )
          (IF (= MOUSE "PR3")
            (PROGN
	      (setq graf 1)
              (fill_image 0 0 773 624 0)
              (activa3 "PR1")
              (activa3 "PR2")
              (activa3 "PR3")
              (activa3 "PR4")
              (activa2 "mapa")
              (activa3 "SEL1")
              (desactiva2 "TOOLSGRF")
              (dibujaelem (BUSOBJBD LISTADCLOBJ 74 "PR1"))
              (dibujaelem (BUSOBJBD LISTADCLOBJ 74 "PR2"))
              (dibujaelem (BUSOBJBD LISTADCLOBJ 74 "PR3"))
              (dibujaelem (BUSOBJBD LISTADCLOBJ 74 "PR4"))
            )
          )
        )
      )
      (IF (= statusobj "1") 
        (PROGN
          (DESPULSA MOUSE)
          (IF (= MOUSE "PR1") 
            (PROGN
              (activa2 "CONSISTENCIA")
              (dibujaelem (BUSOBJBD LISTADCLOBJ2 274 "CONSIST1"))
              (dibujaelem (BUSOBJBD LISTADCLOBJ2 274 "CONSIST2"))
              (dibujaelem (BUSOBJBD LISTADCLOBJ 74 "CONSEJE1"))
              (dibujaelem (BUSOBJBD LISTADCLOBJ 74 "CONSEJE2"))
            )
          )
          (IF (= MOUSE "PR4") 
            (PROGN
	      (SETQ DATOSFT5 (investigobj "DATOSF5"))
	      (IF (OR (= DATOSFT5 2)(= DATOSFT5 3))
	      (progn
	      (dialogorep)
	      (DESactiva2 "RESUMEN")
	      )
	      (progn
              (activa2 "RESUMEN")
	      (dibujaelem (BUSOBJBD LISTADCLOBJ2 274 "RESUM1"))
              (dibujaelem (BUSOBJBD LISTADCLOBJ 74 "RESUMEJE1")))
	      )
            )
          )
          (IF (= MOUSE "PR3") 
            (PROGN
	      (setq graf 1)
              (ggrafic)
            )
          )
          (IF (= MOUSE "PR2") 
            (PROGN
              (activa2 "LLENA")
              (dibujaelem (BUSOBJBD LISTADCLOBJ2 274 "LLENA1"))
              (dibujaelem (BUSOBJBD LISTADCLOBJ2 274 "LLENA2"))
              (dibujaelem (BUSOBJBD LISTADCLOBJ 74 "LLENAEJE1"))
              (dibujaelem (BUSOBJBD LISTADCLOBJ 74 "LLENAEJE2"))
            )
          )
        )
      )
    )
  )
  (IF (= MOUSE "EJEGRFC")
   (progn
                (fill_image 414 381 360 243 252)
                (fill_image 414 381 360 20 105)
                (fill_image 414 450 360 20 105)
                (fill_image 505 411 115 15 253)
                (fill_image 505 431 115 15 253)
                (slide_image 414 381 360 243 (STRCAT RUTA "SLIDES\\CMBStEnD.sld"))
                (activa2 "rctobj")
                (dibujaelem (BUSOBJBD LISTADCLOBJ 74 "RCT01"))
                (dibujaelem (BUSOBJBD LISTADCLOBJ 74 "RCT02"))
                (dibujaelem (BUSOBJBD LISTADCLOBJ 74 "RCT03"))
                (dibujaelem (BUSOBJBD LISTADCLOBJ 74 "RCT04"))
                (dibujaelem (BUSOBJBD LISTADCLOBJ 74 "RCT05"))
                (dibujaelem (BUSOBJBD LISTADCLOBJ 74 "RCT06"))
                (dibujaelem (BUSOBJBD LISTADCLOBJ 74 "EJEGRFC"))
                (SETQ FECHAINIX (ftofcad (substr vargrf2 4 8)))
                (SETQ FECHAFINX (ftofcad (substr vargrf2 12 8)))
                (stextoj FECHAINIX "romans" 12 510 424 "C")
                (stextoj FECHAFINX "romans" 12 510 445 "C")
     (setq tipogrf "")
     (SETQ tipogrf (investigobj "ACC03"))
     (if (= "1" tipogrf) (setq tipogrf "BR"))
     (if (= tipogrf "0")
       (progn
         (SETQ tipogrf (investigobj "ACC04"))
         (if (= "1" tipogrf) (setq tipogrf "LI"))
       )
     )
     (if (= tipogrf "0")
       (progn
         (SETQ tipogrf (investigobj "ACC05"))
         (if (= "1" tipogrf) (setq tipogrf "DS"))
       )
     )
     (SETQ tipodatf (investigobj "DATOSF1"))
     (SETQ datoclimagrf (investigobj "DATOSF2"))
     (SETQ tipoPROf (investigobj "DATOSF3"))
     (SETQ FECHAINIX (ftofcad (substr vargrf2 4 8)))
     (SETQ FECHAFINX (ftofcad (substr vargrf2 12 8)))
     (setq resultadotk (tmankendall (car (nestacc3 nest)) (substr procedencia 1 1) datoclimagrf FECHAINIx FECHAFINx "ME" tipoPROf))
     (setq resultadorl (regresionl (car (nestacc3 nest)) (substr procedencia 1 1) datoclimagrf FECHAINIx FECHAFINx  "ME" tipoPROf));tipodatf
     (setq contecua 1)
     (repeat 12
;       (stexto (rtos (cadddr (assoc contecua resultadotk)) 2 3) "romans" 12 490 (+ (* (1- contecua) 13) 468))
       (setq vecua1 (cadr (assoc contecua resultadotk)))
       (setq vecua2 (caddr (assoc contecua resultadotk)))
       (setq ecua1 (strcat (rtos (atof vecua1) 2 3) "X + " (rtos (atof vecua2) 2 3)))
       (stexto ecua1 "romans" 12 416 (+ (* (1- contecua) 13) 468))
;       (stexto (strcat "R = " (rtos (cadddr (assoc contecua resultadorl)) 2 3)) "romans" 12 674 (+ (* (1- contecua) 13) 468))
       (setq vecua1 (cadr (assoc contecua resultadorl)))
       (setq vecua2 (caddr (assoc contecua resultadorl)))
       (setq ecua1 (strcat (rtos vecua1 2 3) "X + " (rtos vecua2 2 3)))
       (stexto ecua1 "romans" 12 600 (+ (* (1- contecua) 13) 468))
       (setq contecua (1+ contecua))
     )
   )
  )  
  (IF (= MOUSE "EJEGRF1")
    (progn
                (fill_image 414 381 360 243 252)
                (fill_image 414 381 360 20 105)
                (fill_image 414 473 360 20 105)
                (fill_image 422 433 95 15 253)
                (fill_image 422 453 95 15 253)
                (fill_image 601 433 95 15 253)
                (fill_image 601 453 95 15 253)
                (slide_image 414 381 360 243 (STRCAT RUTA "SLIDES\\CMBSmED.sld"))
                (activa2 "rcmobj")
                (dibujaelem (BUSOBJBD LISTADCLOBJ 74 "RCM01"))
                (dibujaelem (BUSOBJBD LISTADCLOBJ 74 "RCM02"))
                (dibujaelem (BUSOBJBD LISTADCLOBJ 74 "RCM03"))
                (dibujaelem (BUSOBJBD LISTADCLOBJ 74 "RCM04"))
                (dibujaelem (BUSOBJBD LISTADCLOBJ 74 "RCM05"))
                (dibujaelem (BUSOBJBD LISTADCLOBJ 74 "RCM06"))
                (dibujaelem (BUSOBJBD LISTADCLOBJ 74 "RCM07"))
                (dibujaelem (BUSOBJBD LISTADCLOBJ 74 "RCM08"))
                (dibujaelem (BUSOBJBD LISTADCLOBJ 74 "RCM09"))
                (dibujaelem (BUSOBJBD LISTADCLOBJ 74 "RCM10"))
                (dibujaelem (BUSOBJBD LISTADCLOBJ 74 "RCM11"))
                (dibujaelem (BUSOBJBD LISTADCLOBJ 74 "RCM12"))
                (dibujaelem (BUSOBJBD LISTADCLOBJ 74 "RCM12"))
                (dibujaelem (BUSOBJBD LISTADCLOBJ 74 "EJEGRF1"))
                (SETQ FECHAINIX (ftofcad (substr vargrf2 4 8)))
                (SETQ FECHAFINX (ftofcad (substr vargrf2 12 8)))
                (stextoj FECHAINIX "romans" 12 430 447 "C")
                (stextoj FECHAFINX "romans" 12 430 467 "C")
                (SETQ FECHAINIX (ftofcad (substr vargrf2 20 8)))
                (SETQ FECHAFINX (ftofcad (substr vargrf2 28 8)))
                (stextoj FECHAINIX "romans" 12 610 447 "C")
                (stextoj FECHAFINX "romans" 12 610 467 "C")
     (setq tipogrf "")
     (SETQ tipogrf (investigobj "ACC03"))
     (if (= "1" tipogrf) (setq tipogrf "BR"))
     (if (= tipogrf "0")
       (progn
         (SETQ tipogrf (investigobj "ACC04"))
         (if (= "1" tipogrf) (setq tipogrf "LI"))
       )
     )
     (if (= tipogrf "0")
       (progn
         (SETQ tipogrf (investigobj "ACC05"))
         (if (= "1" tipogrf) (setq tipogrf "DS"))
       )
     )
     (SETQ tipodat (investigobj "DATOSF1"))
     (SETQ datoclimagrf (investigobj "DATOSF2"))
     (SETQ tipoPROf (investigobj "DATOSF3"))
     (SETQ FECHAINI (substr vargrf2 4 8))
     (SETQ FECHAFIN (substr vargrf2 12 8))
     (setq bd1 (leebd estacion (substr procedencia 1 1) datoclimagrf fechaini tipodat tipoprof))
     (setq nelementosi1 (cuentaer2 fechaini fechafin tipodat))
     (SETQ FECHAINI (substr vargrf2 20 8))
     (SETQ FECHAFIN (substr vargrf2 28 8))
     (setq bd2 (leebd estacion (substr procedencia 1 1) datoclimagrf fechaini tipodat tipoprof))
     (setq nelementosi2 (cuentaer2 fechaini fechafin tipodat))
      (if (= datoclimagrf 1) (setq anchochr 6))
      (if (= datoclimagrf 2) (setq anchochr 1))
      (if (= datoclimagrf 3) (setq anchochr 6))
      (if (= datoclimagrf 4) (setq anchochr 1))
      (if (= datoclimagrf 5) (setq anchochr 1))
      (if (= datoclimagrf 6) (setq anchochr 1))
      (if (= datoclimagrf 7) (setq anchochr 5))
      (if (= datoclimagrf 8) (setq anchochr 5))
      (if (= datoclimagrf 9) (setq anchochr 5))
      (if (AND (OR (= datoclimagrf 1) (= datoclimagrf 3)) (OR (= tipoprof "MA") (= tipoprof "MI") (= tipoprof "ME")))
        (SETQ CARYf 6)
      )
      (if (AND (OR (= datoclimagrf 7) (= datoclimagrf 8) (= datoclimagrf 9)) (OR (= tipoprof "MA") (= tipoprof "MI") (= tipoprof "ME")) )
        (SETQ CARYf 5)
      )
      (if (= tipoprof "TO")
        (SETQ CARYf 9)
      )
      (if (= tipoprof "VC")
        (SETQ CARYf 5)
      )
      (if (and (or (= datoclimagrf 2) (= datoclimagrf 4) (= datoclimagrf 5) (= datoclimagrf 6)) (/= tipoprof "VC"))
        (SETQ CARYf 1)
      )
      (if (= tipodat "ST")
        (PROGN
          (SETQ CARXf 6)
          (SETQ CARYf ANCHOCHR)
        )
        (SETQ CARXf 4)
      )
      (setq bd1 (substr bd1 1 (* nelementosi1 (+ carxf caryf))))
      (setq bd2 (substr bd2 1 (* nelementosi2 (+ carxf caryf))))
      (setq reportestu (teststud bd1 bd2 carxf caryf))
      (setq reportestul reportelist2)
      (setq reportecra (testcram bd1 bd2 carxf caryf))
      (setq reportecral reportelist2)       
      (stexto (cdr (assoc 1 reportestul)) "romans" 12 500 496)
      (stexto (cdr (assoc 2 reportestul)) "romans" 12 500 510)
      (stexto (cdr (assoc 3 reportestul)) "romans" 12 440 523)
      (stexto (cdr (assoc 4 reportestul)) "romans" 12 440 537)
      (stexto (cdr (assoc 5 reportestul)) "romans" 12 440 551)
      (stexto (substr (cdr (assoc 6 reportestul)) 1 25) "romans" 15 419 580)
      (if (> (strlen (cdr (assoc 6 reportestul))) 25)
        (stexto (substr (cdr (assoc 6 reportestul)) 26 25) "romans" 15 419 594)
      )
      (if (> (strlen (cdr (assoc 6 reportestul))) 50)
        (stexto (substr (cdr (assoc 6 reportestul)) 51 25) "romans" 15 419 605)
      )
      (stexto (cdr (assoc 1 reportecral)) "romans" 12 680 496)
      (stexto (cdr (assoc 2 reportecral)) "romans" 12 680 510)
      (stexto (cdr (assoc 3 reportecral)) "romans" 12 622 523)
      (stexto (cdr (assoc 4 reportecral)) "romans" 12 622 537)
      (stexto (cdr (assoc 5 reportecral)) "romans" 12 622 551)
      (stexto (substr (cdr (assoc 6 reportecral)) 1 25) "romans" 15 600 580)
      (if (> (strlen (cdr (assoc 6 reportecral))) 25)
        (stexto (substr (cdr (assoc 6 reportecral)) 26 25) "romans" 15 600 594)
      )
      (if (> (strlen (cdr (assoc 6 reportecral))) 50)
        (stexto (substr (cdr (assoc 6 reportecral)) 51 25) "romans" 15 600 605)
      )
    )
  )
  (if (= graf 1)                                       
   (progn
    (if (> y 325) 
      (if (< y 335)
        (if (and (> x 90) (< x 590))
          (progn
            (SETQ FECHAINI (substr vargrf2 4 8))
            (setq xcor1r  (- x 350))
            (setq xcor2r  (- x 20))
            (setq distar1 (- xcor1r ral1))
            (setq distar2 (- xcor1r ral2))
            (if (< (abs distar1) (Abs distar2))
	      (progn
	        (setq ral1 (+ xcor1r 0))
	        (setq ranga1 (- xcor2r 0))
              )
              (progn
	        (setq ral2 (+ xcor1r 0))
	        (setq ranga2 (- xcor2r 0))
              );progn
            );if
            (rangosest)
            (SETQ PRANGA1X (- RANGA1 90))
            (SETQ PRANGA2X (- RANGA2 90))
            (SETQ PRANGB1X (- RANGB1 90))
            (SETQ PRANGB2X (- RANGB2 90))
            (IF (<= PRANGA1X 0)
              (SETQ PRANGA1X (+ (atoi (substr FECHAINI 1 4)) (* (atoi (substr FECHAINI 5 2)) 0.083333333)))
              (PROGN
                (SETQ DREALX (/ (* PRANGA1X ANCHOGRFVAL) 500.00))
                (SETQ PRANGA1X (+ (atoi (substr FECHAINIGRF 1 4)) DREALX))
              )
            )
            (IF (<= PRANGB1X 0)
              (SETQ PRANGB1X (+ (atoi (substr FECHAINI 1 4)) (* (atoi (substr FECHAINI 5 2)) 0.083333333)))
              (PROGN
                (SETQ DREALX (/ (* PRANGB1X ANCHOGRFVAL) 500.00))
                (SETQ PRANGB1X (+ (atoi (substr FECHAINIGRF 1 4)) DREALX))
              )
            )
            (SETQ DREALX (/ (* PRANGA2X ANCHOGRFVAL) 500.00))
            (SETQ PRANGA2X (+ (atoi (substr FECHAINIGRF 1 4)) DREALX))
            (SETQ DREALX (/ (* PRANGB2X ANCHOGRFVAL) 500.00))
            (SETQ PRANGB2X (+ (atoi (substr FECHAINIGRF 1 4)) DREALX))
            (SETQ PRANGA1XM (- PRANGA1X (FIX PRANGA1X)))
            (SETQ PRANGA2XM (- PRANGA2X (FIX PRANGA2X)))
            (SETQ PRANGB1XM (- PRANGB1X (FIX PRANGB1X)))
            (SETQ PRANGB2XM (- PRANGB2X (FIX PRANGB2X)))
            (SETQ PRANGA1X (STRCAT (ITOA (FIX PRANGA1X)) (DEFINEMES PRANGA1XM) "01"))
            (SETQ PRANGA2X (STRCAT (ITOA (FIX PRANGA2X)) (DEFINEMES PRANGA2XM) "01"))
            (SETQ PRANGB1X (STRCAT (ITOA (FIX PRANGB1X)) (DEFINEMES PRANGB1XM) "01"))
            (SETQ PRANGB2X (STRCAT (ITOA (FIX PRANGB2X)) (DEFINEMES PRANGB2XM) "01"))
            (setq VARGRF2 (strcat (substr vargrf2 1 3) PRANGA1X PRANGA2X PRANGB1X PRANGB2X (substr vargrf2 36)))
          );progn
        );progn
      );if
    );progn
     (if (> y 343) 
        (if (< y 352)
           (if (and (> x 90) (< x 590))
             (progn
               (SETQ FECHAINI (substr vargrf2 4 8))
	       (setq xcor1r  (- x 378))
               (setq xcor2r  (- x 20))
               (setq distar1 (- xcor1r rbl1))
               (setq distar2 (- xcor1r rbl2))
               (if (< (abs distar1) (Abs distar2))
	         (progn
                   (setq rbl1 (+ xcor1r 0))
                   (setq rangb1 (- xcor2r 0))
                 )
                 (progn
                   (setq rbl2 (+ xcor1r 0))
                   (setq rangb2 (- xcor2r 0))
                 )
               );if
               (rangosest)
               (SETQ PRANGA1X (- RANGA1 90))
               (SETQ PRANGA2X (- RANGA2 90))
               (SETQ PRANGB1X (- RANGB1 90))
               (SETQ PRANGB2X (- RANGB2 90))
               (IF (<= PRANGA1X 0)
                 (SETQ PRANGA1X (+ (atoi (substr FECHAINI 1 4)) (* (atoi (substr FECHAINI 5 2)) 0.083333333)))
                 (PROGN
                   (SETQ DREALX (/ (* PRANGA1X ANCHOGRFVAL) 500.00))
                   (SETQ PRANGA1X (+ (atoi (substr FECHAINIGRF 1 4)) DREALX))
                 )
               )
               (IF (<= PRANGB1X 0)
                 (SETQ PRANGB1X (+ (atoi (substr FECHAINI 1 4)) (* (atoi (substr FECHAINI 5 2)) 0.083333333)))
                 (PROGN
                   (SETQ DREALX (/ (* PRANGB1X ANCHOGRFVAL) 500.00))
                   (SETQ PRANGB1X (+ (atoi (substr FECHAINIGRF 1 4)) DREALX))
                 )
               )
               (SETQ DREALX (/ (* PRANGA2X ANCHOGRFVAL) 500.00))
               (SETQ PRANGA2X (+ (atoi (substr FECHAINIGRF 1 4)) DREALX))
               (SETQ DREALX (/ (* PRANGB2X ANCHOGRFVAL) 500.00))
               (SETQ PRANGB2X (+ (atoi (substr FECHAINIGRF 1 4)) DREALX))
               (SETQ PRANGA1XM (- PRANGA1X (FIX PRANGA1X)))
               (SETQ PRANGA2XM (- PRANGA2X (FIX PRANGA2X)))
               (SETQ PRANGB1XM (- PRANGB1X (FIX PRANGB1X)))
               (SETQ PRANGB2XM (- PRANGB2X (FIX PRANGB2X)))
               (SETQ PRANGA1X (STRCAT (ITOA (FIX PRANGA1X)) (DEFINEMES PRANGA1XM) "01"))
               (SETQ PRANGA2X (STRCAT (ITOA (FIX PRANGA2X)) (DEFINEMES PRANGA2XM) "01"))
               (SETQ PRANGB1X (STRCAT (ITOA (FIX PRANGB1X)) (DEFINEMES PRANGB1XM) "01"))
               (SETQ PRANGB2X (STRCAT (ITOA (FIX PRANGB2X)) (DEFINEMES PRANGB2XM) "01"))
               (setq VARGRF2 (strcat (substr vargrf2 1 3) PRANGA1X PRANGA2X PRANGB1X PRANGB2X (substr vargrf2 36)))
             );progn
          );if
        );if
      );if  
    )
   );if
       
     (if (and(= mouse "FABA")(/= estanext "no"));FARR????NO FUNCIONA
       (progn
         (setq ncicloscont (1+ ncicloscont))
         (muestraestace)
       );progn
     );if

     (if (and(= mouse "FARR")(/= estaback "no"));??? faba no funciona
       (progn
             (setq ncicloscont (1- ncicloscont))
             (setq estcontp (- ntestm (* 14 ncicloscont)))
             (setq nestemoss (- estcontp (- ntestm (+ nestclic contcli))))
             (setq nestmostclic (- nestemoss contcli))
             (setq nestmosteric (- nestemoss (+ conteric contcli)))
             (if (= ncicloscont 1)(progn (setq nestclic(+ nestclic contcli))(setq nesterics (+ nesterics conteric))(setq conteric 0)(setq contcli 0)))
             (if (> ncicloscont 1)
               (progn
                 (setq nestclic nestfc)(setq nesterics nestfe)(setq namosi (* (1- ncicloscont) 14))(setq contcli 0)(setq conteric 0)
                 (while (> (1+ namosi) 0)
                 (if (/= nestclic 0)
                   (progn
                     (setq nestclic (1- nestclic))
                     (setq contcli (1+ contcli))
                   )	
                   (progn
                     (setq conteric (1+ conteric))
                     (setq nesterics (1- nesterics))
                   )
                 );if
                 (setq namosi (1- namosi))
                 );while
               );progn
             );if
             (muestraestace)
           );if
     )
;     (if (AND(< estanumeindice (+ nestfc nestfe))(= graf 1))
;       (colocadata)
;     )
     (if (= graf 1)
       (if (and(> xesta 678)(< xesta 752))
         (if (and(> yesta 97)(< yesta 347))
           (progn
             (setq yestaselec y)(setq yestaini 99 )(setq estanumeindice -1)
             (setq estcontp (- ntestm (* 14 (1- ncicloscont))))
             (setq nestemoss (- estcontp (- ntestm (+ nestclic contcli))))
             (while (> yestaselec  yestaini)
               (setq yestaini  (+ 18  yestaini ))
               (setq estanumeindice (1+ estanumeindice))
             )
             (setq estanumeindice (+ estanumeindice (* 14 (1- ncicloscont))))
	       ;(alert estanumeindice)
	       ;(setq nestach (1+ estanumeindice))
	      (if (< estanumeindice ntestm)
	      (actualizagraf2)
	      )
	   )
         )
       )
     );if
  (IF (= MOUSE "INDICE1") 
    (PROGN
      (setq ACCION (seccuad "IND01IND02IND03IND04IND05IND06IND07IND08IND09IND10IND11IND12" 65 216 1 12 6 401 x y))
;      (start_image "imagen") 
      (atzindice2 (substr fechainiex 1 4) (substr fechafinex 1 4) (substr ACCION 4 2))
;      (end_image)
    )
  )
  (IF (= MOUSE "INDICE2") 
    (PROGN
      (setq ACCION (seccuad "IND201IND202IND203IND204IND205IND206IND207IND208IND209IND210IND211IND212IND213IND214IND215IND216IND217IND218IND219IND220" 76 178 2 10 83 401 x y))
      (ALERT ACCION)
    )
  )
;     (if (= graf 1)
;       (if (and(> xesta 778)(< xesta 788))
;         (progn
;           (if (and(> yesta 505)(< yesta 515))(setq indicerangsum 20))
;           (if (and(> yesta 487)(< yesta 496))(setq indicerangsum 10))
;           (if (and(> yesta 520)(< yesta 531))(setq indicerangsum 30))
;           (if (and(> yesta 535)(< yesta 546))(setq indicerangsum 40))
;           (indicegenera)
;         )
;       )
;     );
;     (if (and(= graf 1)(> xesta 6)(< xesta 73))
;       (if (> yesta 404)
;         (progn
;           (indicegenera)
;           (indicemenores)
;         )
;       )
;     )
                                                   
  (end_image)
)
 
(defun cuentaer2 (fechaini fechafin tipodat);(cuentaer2 fechaini fechafin tipoprof)
  (if (= tipodat "AN")
    (setq nelementos (- (atoi (substr fechafin 1 4)) (atoi (substr fechaini 1 4))))
  )
  (if (= tipodat "ME")
    (progn
      (setq fret (substr fechaini 1 6))
      (setq nelementos 1)
      (while (/= fret (substr fechafin 1 6))
        (setq fret (mesmas fret))
        (setq nelementos (1+ nelementos))
      )
    )
  )
  (if (= tipodat "ST")
    (progn
      (setq fret (substr fechaini 1 6))
      (setq nelementos 1)
      (while (/= fret (substr fechafin 1 6))
        (setq mes (substr fret 5 2))
        (if (= mes "01") (setq ndias 31))
        (if (= mes "03") (setq ndias 31))
        (if (= mes "04") (setq ndias 30))
        (if (= mes "05") (setq ndias 31))
        (if (= mes "06") (setq ndias 30))
        (if (= mes "07") (setq ndias 31))
        (if (= mes "08") (setq ndias 31))
        (if (= mes "09") (setq ndias 30))
        (if (= mes "10") (setq ndias 31))
        (if (= mes "11") (setq ndias 30))
        (if (= mes "12") (setq ndias 31))
        (if (= mes "02")
          (progn
            (setq fx (atoi (substr fret 1 4)))
            (setq dx (* (fix (/ fx 4)) 4))
            (if (= dx fx)
               (setq ndias 29)
               (setq ndias 28)
            )
          )
        );if
        (setq fret (mesmas fret))
        (if (= nelementos 0)
          (setq nelementos (+ nelementos (- ndias (1- (atoi (substr fechaini 7 2))))))
          (setq nelementos (+ nelementos ndias))
        )
      )
      (setq mes (substr fret 5 2))
      (if (= mes "01") (setq ndias 31))
      (if (= mes "03") (setq ndias 31))
      (if (= mes "04") (setq ndias 30))
      (if (= mes "05") (setq ndias 31))
      (if (= mes "06") (setq ndias 30))
      (if (= mes "07") (setq ndias 31))
      (if (= mes "08") (setq ndias 31))
      (if (= mes "09") (setq ndias 30))
      (if (= mes "10") (setq ndias 31))
      (if (= mes "11") (setq ndias 30))
      (if (= mes "12") (setq ndias 31))
      (if (= mes "02")
        (progn
          (setq fx (atoi (substr fret 1 4)))
          (setq dx (* (fix (/ fx 4)) 4))
          (if (= dx fx)
             (setq ndias 29)
             (setq ndias 28)
          )
        )
      );if
      (setq nelementos (+ nelementos ndias))
      (setq nelementos (- nelementos (- ndias (1- (atoi (substr fechafin 7 2))))))
    );progn
  )
  (if (= tipodat "MM")
    (setq nelementos 12)
  )
  (setq nelementos nelementos)
)

(defun dibuja3 ()
  (fill_image 0 0 770 650 0);modifique xinicail y inicial anchomapa alto mapa
  (SETQ CUEVER 0)
  (setq verpol (cdr (assoc cuever MATRIZDIBU)))
  (WHILE VERPOL
    (SETQ VERPOL2 VERPOL)
    (SETQ CUEVER (1+ CUEVER))
    (setq verpol (cdr (assoc cuever MATRIZDIBU)))
    (IF (AND VERPOL (/= CUEVER 0))
      (PROGN
        (SETQ X1 (ATOI (RTOS (CAR VERPOL2) 2 0))) 
        (SETQ Y1 (ATOI (RTOS (CADR VERPOL2) 2 0)))
        (SETQ X2 (ATOI (RTOS (CAR VERPOL) 2 0))) 
        (SETQ Y2 (ATOI (RTOS (CADR VERPOL) 2 0)))
        (vector_image X1 Y1 X2 Y2 1)
      )
    )
  )
  (if (= barra1 nil) (setq barra1 1))
  (if (= barra2 nil) (setq barra2 1))
  (if (/= MATRIZEST nil)
   (progn
    (SETQ CUEVER 0)
    (setq verpol (cdr (assoc cuever MATRIZEST)))
    (setq verpolxxx (cadr (assoc (1+ cuever) estaciones3)))	
    (SETQ CONTANIM 1)
    (dos_waitcursor t)
    (dos_getprogress "Trabajando" "Dibujando estaciones" barra1)
    (WHILE VERPOL
      (SETQ X (ATOI (RTOS (CAR VERPOL) 2 0))) 
      (SETQ Y (ATOI (RTOS (CADR VERPOL) 2 0)))
      (slide_image (- X 20) (- Y 20) 40 40 (STRCAT RUTA "SLIDES\\eazul.SLD"))
      (if (< contanim barra1)
        (anim2) 
      )
      (stexto verpolxxx "romans" 18 (- X 20) (- Y 40))
      (SETQ CUEVER (1+ CUEVER))
      (setq verpol (cdr (assoc cuever MATRIZEST)))
      (setq verpolxxx (cadr (assoc (1+ cuever) estaciones3)))	
    )
    (dos_getprogress t)
    (dos_waitcursor)
   )
  )
  (if (/= MATRIZEST2 nil)
   (progn
    (SETQ CUEVER 0)
    (setq verpol (cdr (assoc cuever MATRIZEST2)))
    (setq verpolxxx (cadr (assoc (1+ cuever) estaciones4)))
    (SETQ CONTANIM 1)	
    (dos_waitcursor t)
    (dos_getprogress "Trabajando" "Dibujando estaciones" barra2)
    (WHILE VERPOL
      (SETQ X (ATOI (RTOS (CAR VERPOL) 2 0))) 
      (SETQ Y (ATOI (RTOS (CADR VERPOL) 2 0)))
      (slide_image (- X 25) (- Y 20) 40 40 (STRCAT RUTA "SLIDES\\eamari.sld"))
      (if (< contanim barra2)
        (anim2) 
      )
      (stexto verpolxxx "romans" 18 (- X 25) (+ Y 20))
      (SETQ CUEVER (1+ CUEVER))
      (setq verpol (cdr (assoc cuever MATRIZEST2)))
      (setq verpolxxx (cadr (assoc (1+ cuever) estaciones4)))	
    )
    (dos_getprogress t)
    (dos_waitcursor)
   )
  )
  (slide_image (+ xinicialmapa 540) (+ yinicialmapa 8) 80 97 (STRCAT RUTA "SLIDES\\MAPA2(NORTE).sld"))
  (slide_image (+ xinicialmapa 10) (+ yinicialmapa 557) 143 63 (STRCAT RUTA "SLIDES\\MAPA2(GENERAL).sld"))
  (slide_image (+ xinicialmapa 475) (+ yinicialmapa 557) 143 60 (STRCAT RUTA "SLIDES\\MAPA2(RESUMEN).sld"))
  (dpuntero2 vzoom)
)
(defun nestacc3 (nest)
  (setq resultado nil)
  (if (and (> nest ntest) (= eclicom "1") (= eeric "1"))
    (setq resultado "no")
  )
  (if (and (<= nest ntest) (= eclicom "1") (= eeric "1"))
    (progn
      (if (<= nest num2)
        (progn
          (setq resultado (cdr (assoc nest estaciones3)));nest-1
          (setq procedencia "CLICOM")
        )
        (progn
          (setq resultado (cdr (assoc (- nest nestfc)  estaciones4)));num2-1
          (setq procedencia "ERIC")
        )
      )
    )
  )
  (if (and (> nest ntest) (= eeric "1") (/= eclicom "1"))
    (setq resultado "no")
  )
  (if (and (<= nest ntest) (= eeric "1") (/= eclicom "1"))
    (progn
      (setq resultado (cdr (assoc nest estaciones4)))
      (setq procedencia "ERIC")
    )
  )
  (if (and (> nest ntest) (/= eeric "1") (= eclicom "1"))
    (setq resultado "no")
  )
  (if (and (<= nest ntest) (/= eeric "1") (= eclicom "1"))
    (progn
      (setq resultado (cdr (assoc nest estaciones3)))
      (setq procedencia "CLICOM")
    )
  )
  (SETQ RESULTADO resultado)
)

(defun desta2 (vzoom)
  (setq xestacion (nestacc3 nest))
  (IF (or (= xestacion "no") (= xestacion nil)) (setq nest 1))
  (setq xestacion (nestacc3 nest))
  (SETQ X (ATOI (RTOS (* (atoi (CADR xestacion)) vzoom) 2 0))) 
  (SETQ Y (ATOI (RTOS (* (atoi (CADDR xestacion)) vzoom) 2 0)))
  (print x)
  (print y)
  (setq xestac2 (nestacc3 nest))
  (setq verpolxxx (car xestac2))	
  (slide_image (- X 20) (- Y 20) 40 40 (STRCAT RUTA "SLIDES\\punteron.sld"))
  (if (<  nest num2)
    (slide_image (- X 20) (- Y 20) 40 40 (STRCAT RUTA "SLIDES\\punteron.sld"))
    (slide_image (- X 25) (- Y 20) 40 40 (STRCAT RUTA "SLIDES\\punteron.sld"))
  )
  (if (= procedencia "CLICOM")
   (progn
     (slide_image (- X 20) (- Y 20) 40 40 (STRCAT RUTA "SLIDES\\eazul.SLD")) 
     (stexto verpolxxx "romans" 18 (- X 20) (- Y 40))
   )
  )
  (if (= procedencia "ERIC")
   (progn
     (slide_image (- X 25) (- Y 20) 40 40 (STRCAT RUTA "SLIDES\\eamari.sld"))
     (stexto verpolxxx "romans" 18 (- X 25) (+ Y 20))
   )
  )
)

(defun dpuntero2 (vzoom)
  (if (/= Xcolocaesta nil)
    (progn
      (fill_image (- Xcolocaesta 25) (- Ycolocaesta 20) 41 41 0)(if(= procedencia "CLICOM")
      (slide_image (- Xcolocaesta 20) (- Ycolocaesta 20) 40 40 (STRCAT RUTA "SLIDES\\eazul.SLD")
    )
    (slide_image (- Xcolocaesta 25) (- Ycolocaesta 20) 40 40 (STRCAT RUTA "SLIDES\\eamari.sld"))))
  )
  (leyenbtn2 nest)
  (setq xestac (nestacc nest))
  (IF (or (= XESTAC "no") (= XESTAC nil)) (setq nest 1))
  (setq xestac (nestacc nest))
  (SETQ Xcolocaesta (ATOI (RTOS (* (CaR XESTAC) vzoom) 2 0))) 
  (SETQ Ycolocaesta (ATOI (RTOS (* (CAdR XESTAC) vzoom) 2 0)))
  (if (<  nest num2)
    (slide_image (- Xcolocaesta 20) (- Ycolocaesta 20) 40 40 (STRCAT RUTA "SLIDES\\puntero.sld"))
    (slide_image (- Xcolocaesta 25) (- Ycolocaesta 20) 40 40 (STRCAT RUTA "SLIDES\\puntero.sld"))
  )
  (SETQ ptX (CAR puntogeo))                       ; distancia
  (SETQ ptY (CADR puntogeo))
  (setq verpolxxx (nestacc3 nest))
  (SETQ ptX2 (ATOf (CAdR verpolxxx))) 
  (SETQ ptY2 (ATOf (CADdR verpolxxx)))
  (setq distanciacnt (* 110668.9215 (distance (list ptx pty) (list ptx2 pty2))))
  (setq distanciacnt (smiles distanciacnt))
  (fill_image 242 571 140 11 0)
  (stexto (Ielevacion (car verpolxxx)) "romans" 12 (+ 242 (* 5 (- 8 (STRLEN (Ielevacion (car verpolxxx)))))) 571)
  (fill_image 254 583 40 11 0)
  (stexto procedencia "romans" 12 (+ 254 (* 5 (- 6 (STRLEN procedencia)))) 583)
  (fill_image 256 595 34 11 0)
  (stexto (car verpolxxx) "romans" 12 (+ 256 (* 5 (- 5 (STRLEN (car verpolxxx))))) 595)
  (fill_image 183 607 114 12 0)
  (stexto distanciacnt "romans" 12 (+ 183 (* 5 (- 18 (STRLEN distanciacnt)))) 607);17
  (SETQ OBJETO (BUSOBJBD LISTADCLOBJ 74 "SEL1"))
  (if (= (estdefinitiva2 nest) "S")
    (setq LINEAFIN (strcat (substr OBJETO 1 31) "1" (substr OBJETO 33)))
    (setq LINEAFIN (strcat (substr OBJETO 1 31) "0" (substr OBJETO 33)))
  )
  (SETQ LISTADCLOBJ (ACTUALIZABD LISTADCLOBJ 74 "SEL1" LINEAFIN))
  (dibujaelem LINEAFIN)
)

(defun leyenbtn2 (nestac)
  (if (> nestac NUM2)
    (setq ldat (cdr (assoc (- nestac NUM2) matrizporcentaje2)))
    (setq ldat (cdr (assoc nestac matrizporcentajc2)))
  )
  (setq fuentescr "romans")
  (SETQ OBJETO (BUSOBJBD LISTADCLOBJ2 274 "DATOSF2"))
  (setq statusobjES (SUBSTR OBJETO 255 20))
  (SETQ NDATOCLIM (NPULSADO statusobjES))
  (IF (/= NDATOCLIM NIL)
    (PROGN
      (setq datocl (cdr (assoc NDATOCLIM ldat)))
      (if (= datocl "XXXXXX") (SETQ DATOCL "XXXXXXXXXXXXXXXXXXXXX"))
      (setq x1ly (+ 10 (* (1- NDATOCLIM) 100)))
      (setq x2ly (+ 70 (* (1- NDATOCLIM) 100)))
      (fill_image 740 570 20 11 0)
      (setq verpolly (itoa (atoi (substr datocl 18 4))))
      (stexto verpolly fuentescr 12 (+ 740 (* 5 (- 3 (STRLEN verpolly)))) 570)
      (setq verpolly (strcat (substr datocl 13 5) "%"))
      (fill_image 721 582 40 11 0)
      (stexto verpolly fuentescr 12 (+ 721 (* 5 (- 6 (STRLEN verpolly)))) 582)
      (setq verpolly (strcat (substr datocl 1 4) "-" (substr datocl 7 4)))
      (fill_image 696 594 62 11 0)
      (stexto verpolly fuentescr 12 (+ 696 (* 5 (- 9 (STRLEN verpolly)))) 594)
      (if (= NDATOCLIM 1) (progn (setq verpolly "Evaporaracion")))
      (if (= NDATOCLIM 2) (progn (setq verpolly "Granizo")))
      (if (= NDATOCLIM 3) (progn (setq verpolly "Precipitacion")))
      (if (= NDATOCLIM 4) (progn (setq verpolly "Neblina")))
      (if (= NDATOCLIM 5) (progn (setq verpolly "Covertura del cielo")))
      (if (= NDATOCLIM 6) (progn (setq verpolly "Torm. Electricas")))
      (if (= NDATOCLIM 7) (progn (setq verpolly "Temperatura")))
      (if (= NDATOCLIM 8) (progn (setq verpolly "Temp. maxima")))
      (if (= NDATOCLIM 9) (progn (setq verpolly "Temp. minima")))
      (fill_image 654 605 106 12 0)
      (stexto verpolly fuentescr 12 (+ 654 (* 5 (- 19 (STRLEN verpolly)))) 605)
    )
  )
)

(DEFUN NPULSADO (CADENAF)
  (SETQ SAL "")
  (SETQ CONTSALDLG 1)
  (SETQ RESULTADO NIL)
  (WHILE (AND (= SAL "") (<= CONTSALDLG 20))
    (IF (= (SUBSTR cadenaF CONTSALDLG 1) "1") 
      (PROGN
        (SETQ RESULTADO CONTSALDLG)
        (SETQ SAL "S")
      )
    )
    (SETQ CONTSALDLG (1+ CONTSALDLG))
  )
  (SETQ RESULTADO RESULTADO)
)

(DEFUN DESPULSA (BOTON)
  (SETQ CONTDESP 1)
  (REPEAT 4
    (IF (/= CONTDESP (ATOI (SUBSTR BOTON 3 1)))
      (PROGN
        (SETQ EVENTOX (STRCAT "PR" (ITOA CONTDESP)))
        (SETQ OBJETO (BUSOBJBD LISTADCLOBJ 74 EVENTOX))
        (setq statusobj (SUBSTR OBJETO 32 1))
        (IF (= statusobj "1") 
          (PROGN
            (IF (= EVENTOX "PR1") 
              (PROGN
                (DESactiva2 "CONSISTENCIA")
                (fill_image 0 0 144 257 0)
              )
            )
            (IF (= EVENTOX "PR4") 
              (PROGN
                (DESactiva2 "RESUMEN")
                 (fill_image 0 0 144 235 0)
              )
            )
            (IF (= EVENTOX "PR2") 
              (PROGN
                (DESactiva2 "LLENA")
                 (fill_image 0 0 144 265 0)
              )
            )
            (IF (= EVENTOX "PR3") 
              (PROGN
                (fill_image 0 0 773 624 0)
                (activa3 "PR1")
                (activa3 "PR2")
                (activa3 "PR3")
                (activa3 "PR4")
                (activa2 "mapa")
                (activa3 "SEL1")
                (desactiva2 "TOOLSGRF")
                (dibujaelem (BUSOBJBD LISTADCLOBJ 74 "PR1"))
                (dibujaelem (BUSOBJBD LISTADCLOBJ 74 "PR2"))
                (dibujaelem (BUSOBJBD LISTADCLOBJ 74 "PR3"))
                (dibujaelem (BUSOBJBD LISTADCLOBJ 74 "PR4"))
              )
            )
            (setq LINEAFIN (strcat (substr OBJETO 1 31) "0" (substr OBJETO 33)))
            (SETQ LISTADCLOBJ (ACTUALIZABD LISTADCLOBJ 74 EVENTOX LINEAFIN))
            (dibujaelem LINEAFIN)
          )
        )
      )
    )
    (SETQ CONTDESP (1+ CONTDESP))
  )
)

(DEFUN DESPULSA2 (BOTON)
  (SETQ CONTDESP 3)
  (REPEAT 3
    (IF (/= CONTDESP (ATOI (SUBSTR BOTON 5 1)))
      (PROGN
        (SETQ EVENTOX (STRCAT "ACC0" (ITOA CONTDESP)))
        (SETQ OBJETO (BUSOBJBD LISTADCLOBJ 74 EVENTOX))
        (setq statusobj (SUBSTR OBJETO 32 1))
        (IF (= statusobj "1") 
          (PROGN
            (setq LINEAFIN (strcat (substr OBJETO 1 31) "0" (substr OBJETO 33)))
            (SETQ LISTADCLOBJ (ACTUALIZABD LISTADCLOBJ 74 EVENTOX LINEAFIN))
            (dibujaelem LINEAFIN)
          )
        )
      )
    )
    (SETQ CONTDESP (1+ CONTDESP))
  )
)

(DEFUN DESPULSA3 (BOTON)
  (SETQ CONTDESP 1)
  (REPEAT 9
    (if (or (= contdesp 1) (= contdesp 2)) (setq CONTDESPf contdesp))
    (if (and (>= contdesp 3) (<= contdesp 8)) (setq CONTDESPf (+ contdesp 3)))
    (if (> contdesp 8) (setq CONTDESPf 14))
    (IF (/= CONTDESPf (ATOI (SUBSTR BOTON 4 2)))
      (PROGN
        (if (<= contdesp 6)
          (SETQ EVENTOX (STRCAT "ACC0" (ITOA CONTDESPf)))
          (SETQ EVENTOX (STRCAT "ACC" (ITOA CONTDESPf)))
        )
        (SETQ OBJETO (BUSOBJBD LISTADCLOBJ 74 EVENTOX))
        (setq statusobj (SUBSTR OBJETO 32 1))
        (IF (= statusobj "1") 
          (PROGN
            (if (= EVENTOX "ACC01")
              (progn
                (desactiva2 "colorgrf1")
              )
            )
            (if (= EVENTOX "ACC02")
              (progn
                (desactiva2 "colorgrf2")
              )
            )
            (if (= EVENTOX "ACC06")
              (progn
                (desactiva2 "rcmobj")
              )
            )
            (if (= EVENTOX "ACC07")
              (progn
                (desactiva2 "rctobj")
              )
            )
            (if (= EVENTOX "ACC08")
              (progn
                (desactiva2 "vmobj")
              )
            )
            (if (= EVENTOX "ACC09")
              (progn
                (desactiva2 "vmiobj")
              )
            )
            (if (= EVENTOX "ACC10")
              (progn
                (desactiva2 "vmeobj")
              )
            )
            (if (= EVENTOX "ACC11")
              (progn
                (desactiva2 "sumobj")
              )
            )
            (if (= EVENTOX "ACC14")
              (progn
                (SETQ OBJETOEV14 (BUSOBJBD LISTADCLOBJ2 274 "SOBRE1"))
;                (ALERT (substr OBJETOEV14 255 2))
                (SETQ L1ST (substr OBJETOEV14 255 2))
                (SETQ OBJETOEV14 (BUSOBJBD LISTADCLOBJ2 274 "SOBRE2"))
;                (ALERT (substr OBJETOEV14 255 4))
                (SETQ L2ST (substr OBJETOEV14 255 4))
                (SETQ OBJETOEV14 (BUSOBJBD LISTADCLOBJ2 274 "SOBRE3"))
;                (ALERT (substr OBJETOEV14 255 3))
                (SETQ L3ST (substr OBJETOEV14 255 3))
                (SETQ VARGRF2 (STRCAT (SUBSTR VARGRF2 1 35) L1ST L2ST L3ST (SUBSTR VARGRF2 45 1)))
                (desactiva2 "sobobj")
              )
            )
            (setq LINEAFIN (strcat (substr OBJETO 1 31) "0" (substr OBJETO 33)))
            (SETQ LISTADCLOBJ (ACTUALIZABD LISTADCLOBJ 74 EVENTOX LINEAFIN))
            (dibujaelem LINEAFIN)
          )
        )
      )
    )
    (SETQ CONTDESP (1+ CONTDESP))
  )
)

(defun investigobj (objetor)
  (if (OR (AND (= (SUBSTR OBJETOR 1 6) "DATOSF") (= (STRLEN OBJETOR) 7)) (= OBJETOR "CONSIST1") (= OBJETOR "CONSIST2") (= OBJETOR "LLENA1") (= OBJETOR "LLENA2") (= OBJETOR "RESUM1"))
    (SETQ TIPOOBJR 2)
    (SETQ TIPOOBJR 1)
  )
  (IF (= TIPOOBJR 2)
    (PROGN
      (SETQ OBJETO (BUSOBJBD LISTADCLOBJ2 274 objetor))
      (setq statusobjES (SUBSTR OBJETO 255 20))
      (SETQ NDATOPULSA (NPULSADO statusobjES))
    )
    (PROGN
      (SETQ OBJETO (BUSOBJBD LISTADCLOBJ 74 objetor))
      (setq RESULTADOI (SUBSTR OBJETO 32 1))
    )
  )
  (IF (AND (= (SUBSTR OBJETOR 1 6) "DATOSF") (= (STRLEN OBJETOR) 7))
    (PROGN
      (IF (= OBJETOR "DATOSF1")
        (PROGN
          (IF (= NDATOPULSA 1) (SETQ RESULTADOI "AN"))
          (IF (= NDATOPULSA 2) (SETQ RESULTADOI "ME"))
          (IF (= NDATOPULSA 3) (SETQ RESULTADOI "ST"))
        )
      )
      (IF (OR (= OBJETOR "DATOSF2") (= OBJETOR "DATOSF4") (= OBJETOR "DATOSF5"))
        (SETQ RESULTADOI NDATOPULSA)
      )
      (IF (= OBJETOR "DATOSF3")
        (PROGN
          (IF (= NDATOPULSA 1) (SETQ RESULTADOI "MA"))
          (IF (= NDATOPULSA 2) (SETQ RESULTADOI "ME"))
          (IF (= NDATOPULSA 3) (SETQ RESULTADOI "MI"))
          (IF (= NDATOPULSA 4) (SETQ RESULTADOI "TO"))
        )
      )
    )
  )
  (IF (AND (/= (SUBSTR OBJETOR 1 6) "DATOSF") (= TIPOOBJR 2))
    (SETQ RESULTADOI NDATOPULSA)
  )
  (SETQ RESULTADOI RESULTADOI)
)

(defun v92 ()
  (start_image "imagen")
  (DESTA2 vzoom)
  (setq nest (1+ nest))
  (if (> nest (+ num2 num3)) (setq nest 1))
  (dpuntero2 vzoom)
  (end_image)
)

(defun v102 ()
  (start_image "imagen")
  (DESTA2 vzoom)
  (if (< 1 nest) 
   (setq nest (1- nest))
   (setq nest (+ num2 num3))
  )
  (dpuntero2 vzoom)
  (end_image)
)

(defun estdefinitiva2 (estbuscada);casa
  (setq decision "")
  (if (> estbuscada num2)
    (progn
      (setq nciclos (/ (strlen ESTACFINALE2) 5))
      (setq varanaliz ESTACFINALE2)
    )
    (progn
      (setq nciclos (/ (strlen ESTACFINALC2) 5))
      (setq varanaliz ESTACFINALC2)
    )
  )
  (setq contadore 1)
   (repeat nciclos
    (setq numero (atoi (substr varanaliz (1+ (* 5 (1- contadore))) 5)))
    (if (= numero estbuscada) (setq decision "S"))
    (setq contadore (1+ contadore))
  )
  (if (= decision "S")
    (setq decision "S")
    (setq decision "N")
  )
)

(defun estdefinitivab2 (estbuscada);casa
  (if (> estbuscada num2)
    (progn
      (setq nciclos (/ (strlen ESTACFINALE2) 5))
      (setq varanaliz ESTACFINALE2)
    )
    (progn
      (setq nciclos (/ (strlen ESTACFINALC2) 5))
      (setq varanaliz ESTACFINALC2)
    )
  )
  (setq contadore 1)
  (repeat nciclos
    (setq numero (atoi (substr varanaliz (1+ (* 5 (1- contadore))) 5)))
    (if (= numero estbuscada) (setq decision contadore))
    (setq contadore (1+ contadore))
  )
  (if (= nciclos 1)
    (if (> estbuscada num2)
      (setq ESTACFINALE2 "")
      (setq ESTACFINALC2 "")
    )
    (if (> estbuscada num2)
      (setq ESTACFINALE2 (strcat (substr varanaliz 1 (* 5 (1- decision))) (substr varanaliz (+ 6 (* 5 (1- decision))))))
      (setq ESTACFINALC2 (strcat (substr varanaliz 1 (* 5 (1- decision))) (substr varanaliz (+ 6 (* 5 (1- decision))))))
    )
  )
)
