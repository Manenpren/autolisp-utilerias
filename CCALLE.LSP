(defun c:CCALLE ()
    (setq block (car (entsel "primer block : ")))
    (setq block2 (car (entsel "segundo block : ")))
    (setq xyz (cdr (assoc 10 (entget block))))
    (setq xyz2 (cdr (assoc 10 (entget block2))))
    (SETQ Y (CADR xyz))
    (SETQ Y (RTOS Y 2 5))
    (SETQ X (CAR xyz))
    (SETQ X (RTOS X 2 5))
    (SETQ Y2 (CADR xyz2))
    (SETQ Y2 (RTOS Y2 2 5))
    (SETQ X2 (CAR xyz2))
    (SETQ X2 (RTOS X2 2 5))
    (setq elev1 (busatr block "ELEV"))
    (setq elev2 (busatr block2 "ELEV"))
    (setq a (angle XYZ XYZ2))
    (setq a (* 180 (/ a pi)))
    (command "snap" "ro" XYZ a)
    (command "snap" "off")
    (COMMAND "ARRAY" BLOCK "" "R" "" "2" ".02" )
    (SETQ XE (ENTLAST))
    (command "change" XE "" "p" "la" "inter" "")
    (SETQ XE (ENTNEXT XE))
    (SETQ XE (ENTNEXT XE))
    (COMMAND "ATTEDIT" "" "" "" "" XE "VALUE" "" (RTOS (- (ATOF ELEV1) 0.15) 2 3) "" "")
    (setq a (angle XYZ2 XYZ))
    (setq a (* 180 (/ a pi)))
    (command "snap" "ro" XYZ2 a)
    (command "snap" "off")
    (COMMAND "ARRAY" BLOCK2 "" "R" "" "2" ".02" )
    (SETQ XE (ENTLAST))
    (command "change" XE "" "p" "la" "inter" "")
    (SETQ XE (ENTNEXT XE))
    (SETQ XE (ENTNEXT XE))
    (COMMAND "ATTEDIT" "" "" "" "" XE "VALUE" "" (RTOS (- (ATOF ELEV2) 0.15) 2 3) "" "")
    (command "line" ".xy" (strcat x "," y) elev1 ".xy" (strcat x2 "," y2) elev2 "")
    (command "snap" "ro" "0,0" "0")
    (command "snap" "off")
  (setq x1 (car xyz))
  (setq y1 (car (cdr xyz)))
  (setq x2 (car xyz2))
  (setq y2 (car (cdr xyz2)))
  (setq xd (- x1 x2))
  (if (> 0 xd)
    (setq xd (* xd -1))
  )
  (setq xd (/ xd 2))

  (setq yd (- y1 y2))
  (if (> 0 yd)
    (setq yd (* yd -1))
  )
  (setq yd (/ yd 2))
  (if (> x1 x2)
    (setq xd (+ xd x2))
    (setq xd (+ xd x1))
  )
  (if (> y1 y2)
    (setq yd (+ yd y2))
    (setq yd (+ yd y1))
  )
  (setq punmid (list xd yd))
  (command "insert" "pun2" punmid ".25" "" "" "INTER" (RTOS (+ (* (distance XYZ PUNMID) 0.02) (- (ATOF ELEV1) 0.15)) 2 3) "XXX" "" "" "")
)

(DEFUN BUSATR (E ATR)
 (SETQ E (ENTNEXT E))
 (SETQ R 0)
 (WHILE (= "ATTRIB" (cdr (assoc 0 (entget E))))
   (if (= "ATTRIB" (cdr (assoc 0 (entget E))))
      (if (= ATR (cdr (assoc 2 (entget E))))
       (PROGN
        (setq vALAT (cdr (assoc 1 (entget E))))
       )
      )
   )
   (SETQ R (1+ R))
   (SETQ E (ENTNEXT E))
 )
 (PRINT ValAT)
)
