(DEFUN C:SECCOMAR ()
  (COMMAND "UNDO" "M")
  (COMMAND "VIEW" "S" "C")
  (C:LIBRERIA "busca block en base de datos")
  (C:LIBRERIA "ZOOM ULTIMO OBJETO INSERTADO")
  (C:LIBRERIA "VERTICES DE UNA LWPOLYLINE")
  (COMMAND "LUNITS" 2)
  (COMMAND "LUPREC" 7)
  (COMMAND "AUNITS" 0)
  (COMMAND "AUPREC" 4)
  (COMMAND "ANGDIR" 0)
  (COMMAND "ANGBASE" 0.0)
  (COMMAND "DIMZIN" 0)
  (prompt "selecciona el grupo de bloques a extraer")
  (setq gpodse (ssget))
  (setq cont2 0)
  (setq block 1)
  (SETQ f1 (OPEN "C:\\SECCIONES.CSV" "w"))
  (while block
   (setq BLOCK (ssname gpodse cont2))
   (if (/= block nil)
    (progn
    (setq cont2 (1+ cont2))
    (setq NOMBLO (cdr (assoc 2 (entget BLOCK))))
    (setq nb2 nomblo)
    (COMMAND "INSERT" NOMBLO "0,0" "" "" "")
    (SETQ X (ENTLAST))
    (ZBLOCK)
    (SETQ POLY (SSGET "P" '((0 . "LWPOLYLINE"))))
    (IF (/= (sslength POLY) 1)
      (PROGN 
        (ALERT "la seccion no tiene polylinea o tiene dos segmentos de ella,corregir y reiniciar programa")
        (close f1)
        (exit)
      )
    )
    (setq pl (ssname poly 0))
    (setq vert (vertice pl 1))
    (setq cont 2)
    (WRITE-LINE "" F1)
    (WRITE-LINE nomblo F1)
    (SETQ XV (CAR vert))
    (SETQ YV (CADR vert))
    (setq ymin yv)
    (setq ymax yv)
    (WRITE-LINE (strcat (rtos xv) "," (rtos yv)) F1)
    (while vert
      (setq vert (vertice pl cont))
      (if (/= vert nil)
        (progn
          (SETQ XV (CAR vert))
          (SETQ YV (CADR vert))
          (WRITE-LINE (strcat (rtos xv) "," (rtos yv)) F1)
          (setq cont (1+ cont))
          (if (> yv ymax) (setq ymax yv))
          (if (< yv ymin) (setq ymin yv))
        )
      )
    )
    (if (> 1 (- ymax ymin))
      (progn
        (ALERT "la seccion tiene un desnivel menor de 1 metros revisar si esta correcta")
        (close f1)
        (exit)
      )
    )
    (COMMAND "ERASE" gpoa "")
    )  			;progn
   )  			;if
  )         		; while
  (close f1)
  (COMMAND "VIEW" "r" "C")
)
