(DEFUN c:INSPUN1 ()
(IF (/= X "LLAMA")
 (PROGN
  (setq lin (car (entsel "\n Selecciona la polylinea a procesar: ")))
  (while (/= "LWPOLYLINE" (cdr (assoc 0 (entget lin))))
      (if (/= "LWPOLYLINE" (cdr (assoc 0 (entget lin))))
        (progn   
          (alert "\nEl objeto debe ser polylinea ")
          (setq lin (car (entsel "\n Selecciona objeto: ")))
        )
      )
  )
 )
)
;  (setq TBl (getstring "Block a insertar en los vertices <PUNTO> :"))
;  (IF (= TBl "") (SETQ TBl "PUNTO"))
  (setq esc (getreal "\n Escala de los bloques a insertar: "))
  (setq PROV (getint "INICIO : " ))
  (SETQ PROV2 1)
  (SETQ VER1 0)
  (SETQ ASOCIA (entget LIN))
  (WHILE VER1
     (SETQ VER1 (VERTICE LIN PROV2))
     (IF (/= VER1 NIL)
      (progn
        (COMMAND "INSERT" (STRCAT RUTA "BLOCKS\\PUNTO") VER1 ESC "" "" PROV "V" "")
        (SETQ ENTP (ENTLAST))
        (SETQ ENTP (ENTNEXT ENTP))
        (COMMAND "ATTEDIT" "" "" "" "" ENTP "V" "R" prov "")
        (SETQ ENTP (ENTNEXT ENTP))
        (COMMAND "ATTEDIT" "" "" "" "" ENTP "V" "R" "V" "")
      )
     )
     (SETQ PROV (+ PROV 1))
     (SETQ PROV2 (+ PROV2 1))
  )
;  (PRINT (VERTICE LIN 1))
)


(defun vertice (poli nov)
  (setq listap (entget poli))
  (setq nver 0)
  (setq salir "N")
  (while (= salir "N")
    (setq sublisp (car listap))
    (if (= 10 (car sublisp))
      (progn
        (setq punto (cdr sublisp))   
        (setq nver (+ nver 1))
      )
    )
    (setq listap (cdr listap))
    (if listap
      (setq salir "N")
      (setq salir "S")
    )
    (if (= nov nver)
      (setq salir "S")
    )
  )
  (if (not listap)
    (setq punto nil)
  )
  (setq punto punto)
)
