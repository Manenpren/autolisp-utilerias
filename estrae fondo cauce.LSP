(DEFUN C:secx ()
  (COMMAND "UNDO" "M")
  (COMMAND "VIEW" "S" "C")
  (C:LIBRERIA "busca block en base de datos")
  (C:LIBRERIA "ZOOM ULTIMO OBJETO INSERTADO")
  (C:LIBRERIA "VERTICES DE UNA LWPOLYLINE")
  (COMMAND "LUNITS" 2)
  (COMMAND "LUPREC" 7)
  (COMMAND "AUNITS" 0)
  (COMMAND "AUPREC" 4)
  (COMMAND "ANGDIR" 0)
  (COMMAND "ANGBASE" 0.0)
  (COMMAND "DIMZIN" 0)
  (prompt "selecciona el grupo de bloques a extraer")
  (setq gpodse (ssget '((0 . "INSERT"))))
  (setq cont2 0)
  (setq block 1)
  (SETQ f1 (OPEN "C:\\SECCIONES.CSV" "w"))
  (while block
   (setq BLOCK (ssname gpodse cont2))
   (if (/= block nil)
     (progn
       (setq cont2 (1+ cont2))
       (setq NOMBLO (cdr (assoc 2 (entget BLOCK))))
       (setq nb2 nomblo)
       (COMMAND "INSERT" NOMBLO "0,0" "" "" "")
       (SETQ X (ENTLAST))
       (ZBLOCK)
       (setq gpot (SSGET "P"))
       (SETQ POLY (SSGET "P" '((0 . "CIRCLE"))))
       (setq ex (ssname poly 0))
       (setq vert (cdr (assoc 10 (entget ex))))
       (SETQ XV (CAR vert))
       (SETQ YV (CADR vert))
       (WRITE-LINE (strcat (rtos xv) "," (rtos yv) "," nomblo) F1)
;       (if (> 1 (- ymax ymin))
;          (progn
;          (ALERT "la seccion tiene un desnivel menor de 1 metros revisar si esta correcta")
;           (close f1)
;           (exit)
;         )
;       )
;       (command "BLOCK" nomblo "Y" "0,0" gpot ex "")
        (command "erase" gpot "")
     )  			;progn
   )  			;if
  )         		; while
  (close f1)
  (COMMAND "VIEW" "r" "C")
)
