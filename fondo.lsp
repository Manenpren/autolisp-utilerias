(defun c:fondo ()
    (SETQ OPCIONESOS (GETVAR "OSMODE"))
    (command "osnap" "none")
    (setq block (car (entsel "primer block : ")))
    (setq block2 (car (entsel "segundo block : ")))
    (setq xyz (cdr (assoc 10 (entget block))))
    (setq xyz2 (cdr (assoc 10 (entget block2))))
    (SETQ Y (CADR xyz))
    (SETQ Y (RTOS Y 2 5))
    (SETQ X (CAR xyz))
    (SETQ X (RTOS X 2 5))
    (SETQ Y2 (CADR xyz2))
    (SETQ Y2 (RTOS Y2 2 5))
    (SETQ X2 (CAR xyz2))
    (SETQ X2 (RTOS X2 2 5))
    (setq elev1 (busatr block "ELEV"))
    (setq elev2 (busatr block2 "ELEV"))
  (setq pun1 xyz) 
  (setq pun2 xyz2) 
  (setq x1 (car pun1))
  (setq y1 (car (cdr pun1)))
  (setq x2 (car pun2))
  (setq y2 (car (cdr pun2)))
  (setq xd (- x1 x2))
  (if (> 0 xd)
    (setq xd (* xd -1))
  )
  (setq xd (/ xd 2))

  (setq yd (- y1 y2))
  (if (> 0 yd)
    (setq yd (* yd -1))
  )
  (setq yd (/ yd 2))
  (if (> x1 x2)
    (setq xd (+ xd x2))
    (setq xd (+ xd x1))
  )
  (if (> y1 y2)
    (setq yd (+ yd y2))
    (setq yd (+ yd y1))
  )
  (setq punmid (list xd yd))  

    (COMMAND "INSERT" (strcat ruta "blocks\\pun2") punmid "0.1" "" "" "fondoi" (rtos (- (/ (+ (atof elev1) (atof elev2)) 2) 0.10) 2 4) "1" "" "" "")
  (SETVAR "OSMODE" OPCIONESOS)
)

(DEFUN BUSATR (E ATR)
 (SETQ E (ENTNEXT E))
 (SETQ R 0)
 (WHILE (= "ATTRIB" (cdr (assoc 0 (entget E))))
   (if (= "ATTRIB" (cdr (assoc 0 (entget E))))
      (if (= ATR (cdr (assoc 2 (entget E))))
       (PROGN
        (setq vALAT (cdr (assoc 1 (entget E))))
       )
      )
   )
   (SETQ R (1+ R))
   (SETQ E (ENTNEXT E))
 )
 (PRINT ValAT)
)
