(defun C:INVPOL ()
    (C:LIBRERIA "VERTICES DE UNA LWPOLYLINE")
    (SETQ LIN (CAR (ENTSEL "\n SELECCIONA LA LINEA A INVERTIR")))
    (setq f 0)
    (SETQ VERY "")
    (while verY
       (setq f (1+ f))
       (SETQ VERY (vertice lin f)) 
    )
    (COMMAND "PLINE")
    (setq f (1- f))
    (SETQ VERY (vertice lin f)) 
    (while verY
       (IF (and (/= VERY NIL) (/= very verx))
          (COMMAND VERY)  
       )
       (setq f (1- f))
       (setq verx very)
       (SETQ VERY (vertice lin f)) 
    )
    (COMMAND "")
)
