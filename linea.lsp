(defun c:linea1 ()
    (SETQ OPCIONESOS (GETVAR "OSMODE"))
    (command "osnap" "none")
    (setq block (car (entsel "primer block : ")))
    (setq block2 (car (entsel "segundo block : ")))
    (setq xyz (cdr (assoc 10 (entget block))))
    (setq xyz2 (cdr (assoc 10 (entget block2))))
    (SETQ Y (CADR xyz))
    (SETQ Y (RTOS Y 2 5))
    (SETQ X (CAR xyz))
    (SETQ X (RTOS X 2 5))
    (SETQ Y2 (CADR xyz2))
    (SETQ Y2 (RTOS Y2 2 5))
    (SETQ X2 (CAR xyz2))
    (SETQ X2 (RTOS X2 2 5))
    (setq elev1 (busatr block "ELEV"))
    (setq elev2 (busatr block2 "ELEV"))
    (command "line" ".xy" (strcat x "," y) elev1 ".xy" (strcat x2 "," y2) elev2 "")
  (SETVAR "OSMODE" OPCIONESOS)
)

(DEFUN BUSATR (E ATR)
 (SETQ E (ENTNEXT E))
 (SETQ R 0)
 (WHILE (= "ATTRIB" (cdr (assoc 0 (entget E))))
   (if (= "ATTRIB" (cdr (assoc 0 (entget E))))
      (if (= ATR (cdr (assoc 2 (entget E))))
       (PROGN
        (setq vALAT (cdr (assoc 1 (entget E))))
       )
      )
   )
   (SETQ R (1+ R))
   (SETQ E (ENTNEXT E))
 )
 (PRINT ValAT)
)
