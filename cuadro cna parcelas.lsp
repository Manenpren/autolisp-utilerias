(defun c:ccna ()
  (command "undo" "m")
  (COMMAND "VIEW" "S" "PROV")
  (SETQ OPCIONESOS (GETVAR "OSMODE"))
  (COMMAND "DIMZIN" 1)
  (command "osnap" "none")
  (COMMAND "LUNITS" 2)
  (COMMAND "LUPREC" 3)
  (COMMAND "AUNITS" 4)
  (COMMAND "AUPREC" 4)
  (COMMAND "ANGDIR" 0)
  (COMMAND "ANGBASE" 0.0)
  (C:LIBRERIA "BUSCA VALOR DE ATRIBUTO")
  (C:LIBRERIA "vertices de una lwpolyline to var")
  (C:LIBRERIA "revisa polilynea ceros,bloques  y zoom")
  (C:LIBRERIA "encuentra block mas cercano a punto")
  (C:LIBRERIA "CUENTA INTERSECCIONES POL")
  (setq lin (car (entsel "\n Selecciona la polylinea a procesar: ")))
  (COMMAND "AREA" "E" LIN)
  (while (/= "LWPOLYLINE" (cdr (assoc 0 (entget lin))))
      (if (/= "LWPOLYLINE" (cdr (assoc 0 (entget lin))))
        (progn   
          (alert "\nEl objeto debe ser polylinea ")
          (setq lin (car (entsel "\n Selecciona objeto: ")))
        )
      )
  )
 (mpun lin)
 (COMMAND "AREA" "E" LIN)
 (setq mvertices (verticebd lin))
 (setq cueverx 1)                                                    ;contador de vertices
 (setq verpol (cdr (assoc 0 mvertices)))                            ;extraccion de datos
 (while verpol
   (setq verpol (cdr (assoc cueverx mvertices)))
   (setq cueverx (+ cueverx 1))
 )
 (setq verpol1 (cdr (assoc 0 mvertices)))                            ;extraccion de datos
 (setq block1 (blocktopto verpol1 0.01))
 (setq xpol1 (rtos (car verpol1) 2 3))
 (setq ypol1 (rtos (car (cdr verpol1)) 2 3))
 (setq codigo1 (BUSATR block1 "PUNTO"))
 (if (= codigo1 nil) (alert "block sin atributo de codigo"))
 (setq elevacion1 (BUSATR block1 "ELEV"))
 (if (= elevacion1 nil) (BUSATR NOMOBJ "ELEVACION"))
 (if (= elevacion1 nil) (alert "block sin atributo de elevacion"))
 (setq cuever 1)
 (SETQ matrizcuadro NIL)
 (setq verpol 1)
 (setq blocki block1)
 (setq xpoli xpol1)
 (setq ypoli ypol1)
 (setq codigoi codigo1)
 (setq elevacioni elevacion1)
 (setq verpoli verpol1)
 (while verpol
   (setq verpol (cdr (assoc cuever mvertices)))
   (IF (/= VERPOL NIL)
    (PROGN
     (setq block (blocktopto verpol 0.01))
     (setq xpol (rtos (car verpol) 2 3))
     (setq ypol (rtos (car (cdr verpol)) 2 3))
     (setq codigo (BUSATR block "PUNTO"))
     (if (= codigo nil) (alert "block sin atributo de codigo"))
     (setq elevacion (BUSATR block "ELEV"))
     (if (= elevacion nil) (BUSATR block "ELEVACION"))
     (if (= elevacion nil) (alert "block sin atributo de elevacion"))
     (setq elevacion (rtos (atof elevacion) 2 3))
     (setq a (angtos (angle verpol1 verpol)))
     (setq aa (formato a))
     (setq aa2 (angtos (- 6.283185307179586476925286766559 (angle verpol1 verpol) -1.5708) 1))
     (setq aa2 (formato aa2))
     (if (= cuever 1)
       (progn
         (setq verpolx (cdr (assoc (- cueverx 2) mvertices)))
         (setq aa3 (abs (- (angle verpolx verpol1) (angle verpol1 verpol))))
       )
       (setq aa3 (abs (- (angle verpolx verpol1) (angle verpol1 verpol))))
     )
     (setq xpolf (rtos (car verpolx) 2 3))
     (setq ypolf (rtos (car (cdr verpolx)) 2 3))
     (setq pmedio (list (- (atof xpol) (/ (- (atof xpol) (atof xpolf)) 2)) (- (atof ypol) (/ (- (atof ypol) (atof ypolf)) 2))))
;                (SETQ XYZX (list 10 (- (atof xpol) (/ (- (atof xpol) (atof xpolf)) 2)) (- (atof ypol) (/ (- (atof ypol) (atof ypolf)) 2))))
;                (ENTMAKE (LIST '(0 . "POINT") '(8 . "0") XYZX))
     (setq rst (INTPOL lin pmedio))
     (if (> aa3 3.1415926535897932384626433832795) (setq aa3 (- 6.283185307179586476925286766559 aa3)))
     (if (= rst "PAR") (setq aa3 (+ 3.1415926535897932384626433832795 aa3)))
     (if (= rst "IMPAR") (setq aa3 (- 3.1415926535897932384626433832795 aa3)))
;     (alert rst)
     (setq aa3 (angtos aa3 1))
     (setq renglon (list (cons 0 (strcat codigo1 "-" codigo)) (cons 2 (rtos (distance verpol1 verpol) 2 3)) (cons 1 aa) (cons 3 aa2) (cons 4 codigo1) (cons 6 Ypol1) (cons 7 Xpol1) (cons 8 elevacion1) (cons 5 aa3)))
     (setq CONCATENADO (cons cuever renglon))
     (setq matrizcuadro (append matrizcuadro (list CONCATENADO)))
     (setq cuever (+ cuever 1))
     (setq block1 block)
     (setq verpolx verpol1)
     (setq xpol1 xpol)
     (setq ypol1 ypol)
     (setq codigo1 codigo)
     (setq elevacion1 elevacion)
     (setq verpol1 verpol)
    )
   ) ;IF
 );WHILE
 (setq a (angtos (angle verpol1 verpolI)))
 (setq aa (formato a))
 (setq aa2 (angtos (- 6.283185307179586476925286766559 (angle verpol1 verpolI) -1.5708) 1))
 (setq aa2 (formato aa2))
     (setq xpolf (rtos (car verpolx) 2 3))
     (setq ypolf (rtos (car (cdr verpolx)) 2 3))
     (setq xpol (rtos (car verpoli) 2 3))
     (setq ypol (rtos (car (cdr verpoli)) 2 3))
     (setq pmedio (list (- (atof xpol) (/ (- (atof xpol) (atof xpolf)) 2)) (- (atof ypol) (/ (- (atof ypol) (atof ypolf)) 2))))
 (setq aa3 (abs (- (angle verpoli verpol1) (angle verpol1 verpolx))))
 (if (> aa3 3.1415926535897932384626433832795) (setq aa3 (- 6.283185307179586476925286766559 aa3)))
     (setq rst (INTPOL lin pmedio))
     (if (= rst "PAR") (setq aa3 (+ 3.1415926535897932384626433832795 aa3)))
     (if (= rst "IMPAR") (setq aa3 (- 3.1415926535897932384626433832795 aa3)))
;                (SETQ XYZX (list 10 (- (atof xpol) (/ (- (atof xpol) (atof xpolf)) 2)) (- (atof ypol) (/ (- (atof ypol) (atof ypolf)) 2))))
;                (ENTMAKE (LIST '(0 . "POINT") '(8 . "0") XYZX))
;     (alert rst)
 (setq aa3 (angtos aa3 1))
 (setq renglon (list (cons 0 (strcat codigo1 "-" codigoi)) (cons 2 (rtos (distance verpol1 verpolI) 2 3)) (cons 1 aa) (cons 3 aa2) (cons 4 codigo1) (cons 6 Ypol1) (cons 7 Xpol1) (cons 8 elevacion1) (cons 5 aa3)))
 (setq CONCATENADO (cons cuever renglon))
 (setq matrizcuadro (append matrizcuadro (list CONCATENADO)))
 (SETQ PDESCARGA (GETPOINT "ESQUINA INFERIOR IZQUIERDA DEL CUADRO :"))
 (setq pdescarga2 pdescarga)
 (SETQ ALTURA (* CUEVER 10.8))
 (SETQ P2 (SUMA PDESCARGA 315.1884 (+ ALTURA 27)))
 (SETQ XYZ (SUMA PDESCARGA 0 ALTURA))
 (command "zoom" pdescarga p2)
 (COMMAND "INSERt" (STRCAT RUTA "BLOCKS\\pparcel\\enc.dwg") xyz "" "" "")
 (COMMAND "INSERt" (STRCAT RUTA "BLOCKS\\pparcel\\superficie.dwg") pdescarga "" "" "")
 (COMMAND "EXPLODE" (ENTLASt) "")
 (setq punretx (cons 10 pdescarga))
 (setq punretx2 (cons 11 xyz))
 (ENTMAKE (LIST '(0 . "LINE") '(100 . "AcDbEntity") '(100 . "AcDbLine") PUNRETX PUNRETX2))
 (SETQ P1 (SUMA PDESCARGA 36 0))
 (SETQ P12 (SUMA PDESCARGA 36 altura))
 (setq punretx (cons 10 p1))
 (setq punretx2 (cons 11 p12))
 (ENTMAKE (LIST '(0 . "LINE") '(100 . "AcDbEntity") '(100 . "AcDbLine") PUNRETX PUNRETX2))
 (SETQ P1 (SUMA PDESCARGA 84.1469 0))
 (SETQ P12 (SUMA PDESCARGA 84.1469 altura))
 (setq punretx (cons 10 p1))
 (setq punretx2 (cons 11 p12))
 (ENTMAKE (LIST '(0 . "LINE") '(100 . "AcDbEntity") '(100 . "AcDbLine") PUNRETX PUNRETX2))
 (SETQ P1 (SUMA PDESCARGA 118.3049 0))
 (SETQ P12 (SUMA PDESCARGA 118.3049 altura))
 (setq punretx (cons 10 p1))
 (setq punretx2 (cons 11 p12))
 (ENTMAKE (LIST '(0 . "LINE") '(100 . "AcDbEntity") '(100 . "AcDbLine") PUNRETX PUNRETX2))
 (SETQ P1 (SUMA PDESCARGA 161.2078 0))
 (SETQ P12 (SUMA PDESCARGA 161.2078 altura))
 (setq punretx (cons 10 p1))
 (setq punretx2 (cons 11 p12))
 (ENTMAKE (LIST '(0 . "LINE") '(100 . "AcDbEntity") '(100 . "AcDbLine") PUNRETX PUNRETX2))
 (SETQ P1 (SUMA PDESCARGA 182.8078 0))
 (SETQ P12 (SUMA PDESCARGA 182.8078 altura))
 (setq punretx (cons 10 p1))
 (setq punretx2 (cons 11 p12))
 (ENTMAKE (LIST '(0 . "LINE") '(100 . "AcDbEntity") '(100 . "AcDbLine") PUNRETX PUNRETX2))
 (SETQ P1 (SUMA PDESCARGA 220.8777 0))
 (SETQ P12 (SUMA PDESCARGA 220.8777 altura))
 (setq punretx (cons 10 p1))
 (setq punretx2 (cons 11 p12))
 (ENTMAKE (LIST '(0 . "LINE") '(100 . "AcDbEntity") '(100 . "AcDbLine") PUNRETX PUNRETX2))
 (SETQ P1 (SUMA PDESCARGA 256.3406 0))
 (SETQ P12 (SUMA PDESCARGA 256.3406 altura))
 (setq punretx (cons 10 p1))
 (setq punretx2 (cons 11 p12))
 (ENTMAKE (LIST '(0 . "LINE") '(100 . "AcDbEntity") '(100 . "AcDbLine") PUNRETX PUNRETX2))
 (SETQ P1 (SUMA PDESCARGA 289.5028 0))
 (SETQ P12 (SUMA PDESCARGA 289.5028 altura))
 (setq punretx (cons 10 p1))
 (setq punretx2 (cons 11 p12))
 (ENTMAKE (LIST '(0 . "LINE") '(100 . "AcDbEntity") '(100 . "AcDbLine") PUNRETX PUNRETX2))
 (SETQ P1 (SUMA PDESCARGA 289.5028 0))
 (SETQ P12 (SUMA PDESCARGA 289.5028 altura))
 (setq punretx (cons 10 p1))
 (setq punretx2 (cons 11 p12))
 (ENTMAKE (LIST '(0 . "LINE") '(100 . "AcDbEntity") '(100 . "AcDbLine") PUNRETX PUNRETX2))
 (SETQ P1 (SUMA PDESCARGA 315.1884 0))
 (SETQ P12 (SUMA PDESCARGA 315.1884 altura))
 (setq punretx (cons 10 p1))
 (setq punretx2 (cons 11 p12))
 (ENTMAKE (LIST '(0 . "LINE") '(100 . "AcDbEntity") '(100 . "AcDbLine") PUNRETX PUNRETX2))
 (setq cont4 cuever)
 (repeat cuever
   (COMMAND "INSERt" (STRCAT RUTA "BLOCKS\\pparcel\\lcd.dwg") pdescarga2 "" "" "")
   (COMMAND "EXPLODE" (ENTLASt) "")
   (COMMAND "INSERt" (STRCAT RUTA "BLOCKS\\pparcel\\TEXTO.dwg") pdescarga2 "" "" "")
   (COMMAND "EXPLODE" (ENTLASt) "")
   (SETQ GPOTXTP (SSGET "P"))
   (SETQ CONT3 0)
   (setq lineac (cdr (assoc cont4 matrizcuadro)))
   (REPEAT 9
      (setq atributoc (cdr (assoc cont3 lineac)))
      (SETQ ENTX (SSNAME GPOTXTP CONT3))
      (setq nte (STRCAT atributoc))
      (entmod (subst (cons 1 nte) (assoc 1 (entget entx)) (entget entx)))
      (SETQ CONT3 (1+ CONT3))
   )
   (SETQ pdescarga2 (SUMA PDESCARGA2 0 10.8))
   (setq cont4 (1- cont4))
 )
 (COMMAND "VIEW" "R" "PROV")
 (SETVAR "OSMODE" OPCIONESOS)
)

(DEFUN SUMA (P VX VY)
  (SETQ X (CAR P))
  (SETQ Y (CAR (CDR P)))
  (LIST (+ X VX) (+ Y VY) (LAST P))
)

(defun formato (datang)
  (write-line datang)
  (if (/= 1 (strlen datang))
    (progn
      (setq cuca 1)
      (while (/= cuca (strlen datang))
        (setq cara (substr datang cuca 1))
        (if (= "d" cara)
          (progn
            (setq t1 (substr datang 1 (- cuca 1)))
            (setq t2 (substr datang (+ cuca 1)))
            (setq datang2 (strcat t1 "%%d" t2))
          )
        )
        (setq cuca (+ cuca 1))
      )
      (setq datang2 datang)
    )
    (setq datang2 datang)
  )
  (setq datang datang2)
)
