(defun cottopo (numero)
   (setq nombre (rtos numero 2 3))
   (setq nombre (rtos (/ (atof nombre) 1000) 2 7))
    (SETQ LNG (STRLEN NOMBRE))
    (SETQ NOMBLO "")
    (SETQ CONT 0)
    (REPEAT LNG
        (SETQ CONT (1+ CONT))
        (setq CARACTER (substr NOMBRE CONT 1))
        (IF (= CARACTER ".") (SETQ CARACTER "+"))
        (setq nomblo (STRCAT NOMBLO CARACTER))
    )
  (setq nomblo (strcat (substr nomblo 1 (- lng 4)) "." (substr nomblo (- lng 3) 3)))
  (setq lng (1+ lng))
  (if (= (substr nomblo (- lng 3) 3) "000") (setq nomblo (substr nomblo 1 (- lng 5))))
  (setq nuetex nomblo)
)


(defun c:CADENA2 ()
  (command "undo" "m")
  (C:LIBRERIA "Carga blocks a pplt")
  (C:LIBRERIA "lee valor de texto de pplt")
  (COMMAND "LUNITS" 2)
  (COMMAND "LUPREC" 7)
  (COMMAND "AUNITS" 0)
  (COMMAND "AUPREC" 4)
  (COMMAND "ANGDIR" 0)
  (COMMAND "ANGBASE" 0.0)
  (COMMAND "DIMZIN" 0)
  (SETQ OPCIONESOS (GETVAR "OSMODE"))
  (command "osnap" "none")
  (C:LIBRERIA "busca block en base de datos")
  (setq lin (car (entsel "Selecciona la linea correspondiente")))
  (setq TipEnt (cdr (assoc 0 (entget lin)))) 
  (setq tipent (strcase tipent))
  (if (and (/= "LWPOLYLINE" TipEnt) (/= "LINE" TipEnt))
    (alert "La entidad que seleccionaste no es una linea")
  ) 

  (setq dcl_id (load_dialog (strcat ruta "dialogos\\cadena.dcl"))) 
  (if (not (new_dialog "CADENA" dcl_id))   
    (exit)                                
                                          
  )
  (setq numerofinallista (ldblpp "Nblock"))
  (set_tile "Nblock" "0")
  (set_tile "cr1" "1")
  (set_tile "inicioc" "20")
  (set_tile "inc" "20")
  (mode_tile "Nblock" 1)
  (action_tile "cr1" "(st_tile_pr1)")
  (action_tile "cr2" "(st_tile_pr2)")
  (action_tile "accept" "(leevar)")
  (action_tile "cancel" "(exit)")
  (start_dialog)                          ; Display the dialog 
                                          ; box.
  (unload_dialog dcl_id)                  ; Unload the DCL file.

  (setq opcion (strcase opcion))
  (if (= opcion "S")
   (progn
    (if (= ancho nil) (setq ancho 20))
    (command "zoom" "c" "0,0" (+ ancho (* ancho 0.15)))
    (setq gpobl (ssadd))
    (command "line" (strcat "0," (rtos (/ ancho 2) 2 3)) (strcat "0," (rtos (* (/ ancho 2) -1) 2 3)) "")
    (ssadd (entlast) gpobl)
    (setq escalt (/ (/ ancho 10) 2.0))
    (command "insert" (strcat ruta "blocks\\textocad") (strcat "0," (rtos (* (/ ancho 2) -1) 2 3)) escalt "" "")
    (command "explode" "l")
    (ssadd (entlast) gpobl)
    (setq valida (sblbd "a$prov1"))
    (if (= valida "S")
      (command "block" "a$prov1" "Y" "0,0" gpobl "")
      (command "block" "a$prov1" "0,0" gpobl "")
    )
    (command "zoom" "p")
    (setq blinsert "a$prov1")
    (setq ttext "a2")
   )
   (progn
     (command "zoom" "c" "0,0" "3")
     (command "insert" blinsert "0,0" "" "" "" "" "" "" "" "" "" "" "" "" "" "" "" "" "" "")
     (setq eprov (entlast))
     (setq e5 (entnext eprov))
     (if (/= e5 nil)
       (setq prov (cdr (assoc 0 (entget e5))))
       (setq prov "m")
     )
     (if (= prov "ATTRIB") 
       (progn
         (setq ttext "attrib") 
         (setq valida (sblbd "a$prov2"))
         (if (= valida "S")
           (command "block" "a$prov2" "Y" "0,0" (entlast) "")
           (command "block" "a$prov2" "0,0" (entlast) "")
         )
         (setq blinsert "a$prov2")
       )
       (progn
         (command "erase" eprov "")
         (setq ttext "a2")
       )
     )
     (command "zoom" "p")
   )
  )
  (COMMAND "MEASURE" LIN "B" blinsert "" IN)
  (SETQ GPOCAD (SSGET "P"))
  (SETQ GPOCAD2 (SSADD))
  (setq e (ssname GpoCAD 0))
  (if (= ttext "a2")
   (progn
    (while E
      (SSDEL E GPOCAD)
      (COMMAND "EXPLODE" E "")
      (SETQ GPOPROV (SSADD))
      (SETQ GPOPROV (SSGET "P"))
      (setq e2 (ssname gpoprov 0))
      (setq nent 1)
      (while e2
        (if (= "TEXT" (cdr (assoc 0 (entget E2))))
         (progn
            (IF (= COMPLEMENTO NIL) (SETQ COMPLEMENTO ""))
            (setq cadd (rtos cadena 2 0))
            (setq nte (cottopo (atof cadd)))
            (setq nte (STRCAT NTE COMPLEMENTO))
            (entmod (subst (cons 1 nte) (assoc 1 (entget e2)) (entget e2)))
            (setq cadena (+ cadena IN))
          )
        )
        (setq e2 (ssname gpoprov nent))
        (setq nent (1+ nent))
      )
      (setq e (ssname GpoCAD 0))
    )
   )
   (progn
    (while E
      (SSDEL E GPOCAD)
      (command "explode" E "")
      (SETQ GPOe (SSADD))
      (SETQ GPOe (SSGET "P"))
      (setq e (ssname gpoe 0))
      (setq e (entnext e))         
      (setq cadd (rtos cadena 2 0))
      (setq nte (cottopo (atof cadd)))
      (setq cadena (+ cadena IN))
      (COMMAND "ATTEDIT" "" "" "" "" e "V" "R" nte "")
      (setq e (ssname gpocad 0))
    )
   )
  )
  (SETVAR "OSMODE" OPCIONESOS)
)

(defun leevar ()
  (setq opcion (get_tile "cr1"))
  (if (/= opcion "1") (setq opcion "N") (setq opcion "S"))
  (setq ancho (atoi (get_tile "ancho")))
  (setq nomblo (get_tile "Nblock"))
  (setq blinsert (rblpp (atoi nomblo) (strcat ruta "PROV.TMP")))
  (setq cadena (atoi (get_tile "inicioc")))
  (setq in (atoi (get_tile "inc")))
  (done_dialog)
)

(defun st_tile_pr1 ()
  (mode_tile "ancho" 0)
  (mode_tile "Nblock" 1)
)

(defun st_tile_pr2 ()
  (mode_tile "ancho" 1)
  (mode_tile "Nblock" 0)
)
