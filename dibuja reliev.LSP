(DEFUN c:drev ()
  (setq NOMARCH (getfiled "ARCHIVO DE DATOS" "" "rel" 32))
  (if (= NOMARCH NIL)
    (exit)
  )
  (setq arch (open nomarch "r"))
  (setq linea (read-line arch))
  (setq sepx (atoi linea))  
  (setq linea (read-line arch))
  (setq sepy (atoi linea))  
  (setq linea (read-line arch))
  (setq xmin (atof linea))  
  (setq linea (read-line arch))
  (setq xmax (atof linea))  
  (setq linea (read-line arch))
  (setq ymin (atof linea))  
  (setq linea (read-line arch))
  (setq ymax (atof linea))
  (setq linea (read-line arch))
  (setq linx (/ xmax sepx))
  (setq liny (/ ymax sepy))
  (command "3dmesh" (rtos sepx 2 0) (rtos sepy 2 0))
  (setq contx 0)
  (setq conty 0)
  (setq linx2 (atof (rtos linx 2 0)))
  (setq liny2 (atof (rtos liny 2 0)))
  (while linea
    (setq punto (strcat (rtos contx) "," (rtos conty) "," linea))
    (command punto)
    (setq conty (+ conty liny2))
    (if (> conty ymax) 
      (progn 
;        (setq linx2 (* linx2 -1)) 
        (setq contx (+ contx linx2))
        (setq conty 0)
      )
    )
;    (if (< contx xmin) 
;      (progn 
;        (setq linx2 (* linx2 -1)) 
;        (setq conty (+ conty liny2))
;        (setq contx xmin)
;      )
;    )
    (setq linea (read-line arch))
  ) 
)

(DEFUN c:drev ()
  (setq NOMARCH (getfiled "ARCHIVO DE DATOS" "" "rel" 32))
  (if (= NOMARCH NIL)
    (exit)
  )
  (setq arch (open nomarch "r"))
  (setq linea (read-line arch))
  (setq sepx (atoi linea))  
  (setq linea (read-line arch))
  (setq sepy (atoi linea))  
  (setq linea (read-line arch))
  (setq xmin (atof linea))  
  (setq linea (read-line arch))
  (setq xmax (atof linea))  
  (setq linea (read-line arch))
  (setq ymin (atof linea))  
  (setq linea (read-line arch))
  (setq ymax (atof linea))
  (setq linea (read-line arch))
  (setq linx (/ xmax sepx))
  (setq liny (/ ymax sepy))
  (command "3dmesh" (rtos sepx 2 0) (rtos sepy 2 0))
  (setq contx 0)
  (setq conty 0)
  (setq linx2 (atof (rtos linx 2 0)))
  (setq liny2 (atof (rtos liny 2 0)))
  (setq conth 0)
  (while linea
    (setq punto (strcat (rtos contx) "," (rtos conty) "," linea))
    (setq contx (+ contx linx2))
    (if (> contx xmax) 
      (progn 
        (setq conty (+ conty liny2))
        (setq contx 0)
      )
    )
    (if (conth 0)
    )
    (if (conth 1)
    )
    (setq linea (read-line arch))
  ) 
)
