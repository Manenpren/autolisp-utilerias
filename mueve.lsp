(defun c:mvo ()
    (setq PUNTO (getpoint " DAME EL PUNTO : "))
    (setq texto (car (entsel "Selecciona el texto: ")))
    (setq NOMBRE (cdr (assoc 1 (entget TEXTO))))
    (print "\n Seleciona los elementos a procesar ")
    (setq gpo (ssget))
    (setq xy (strcat "0," NOMBRE))
    (command "MOVE" gpo "" PUNTO xy)
    (COMMAND "ZOOM" "C" XY "13")
)
