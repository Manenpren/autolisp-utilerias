(DEFUN C:PELEV ()
    (setq PUNTO (getpoint " ELEVACION A TOMAR : "))
    (setq BLOCK (car (entsel "Selecciona el BLOCK: ")))
    (SETQ BLOCK (ENTNEXT BLOCK))
    (SETQ BLOCK (ENTNEXT BLOCK))
    (SETQ Z (RTOS (CADDR PUNTO) 2 3))
    (COMMAND "attedit" "" "" "" "" BLOCK "V" "R" Z "")
)

(DEFUN C:PEL2 ()
    (SETQ OPCIONESOS (GETVAR "OSMODE"))
    (SETVAR "OSMODE" 512)
    (setq PUNTO (getpoint " ELEVACION A TOMAR : "))
    (command "osnap" "none")
    (SETQ Y (CADR PUNTO))
    (SETQ Y (RTOS Y 2 3))
    (SETQ X (CAR PUNTO))
    (SETQ X (RTOS X 2 3))
    (SETQ Z (RTOS (CADDR PUNTO) 2 3))
    (COMMAND "INSERT" (STRCAT RUTA "BLOCKS\\PUN2") (STRCAT X "," Y) ".5" "" "" "" "" "" "" "" "")
    (SETQ ENTP(ENTLAST))
    (SETQ ENTP(ENTNEXT ENTP))
    (COMMAND "ATTEDIT" "" "" "" "" ENTP "V" "R" "int" "") 
    (SETQ ENTP(ENTNEXT ENTP))
    (COMMAND "ATTEDIT" "" "" "" "" ENTP "V" "R" z "") 
    (SETQ ENTP(ENTNEXT ENTP))
    (COMMAND "ATTEDIT" "" "" "" "" ENTP "V" "R" "1" "") 
    (SETVAR "OSMODE" OPCIONESOS)
)
