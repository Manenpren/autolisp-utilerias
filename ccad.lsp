(setq listadatos "1974.3339.3100000001974.4178.9741935481974.5005.7166666671974.5834.3612903231974.6674.5838709681974.7504.6533333331974.8335.2806451611974.9174.8133333331975.0005.1612903231975.0834.8248387101975.1677.0392857141975.2508.4967741941975.3339.6533333331975.4177.9193548391975.5005.7166666671975.5834.2225806451975.6674.0709677421975.7504.5666666671975.8335.7322580651975.9175.8933333331976.0005.4677419351976.0836.3161290321976.1677.275862069")
(defun signifi (datoexs)
  (setq nmeses (/ (strlen datoexs) (+ 8 cary)))
  (SETQ S 0)
  (SETQ K 1)
  (setq htpkendall "")
  (setq gkendall 0)
  (setq srf "")
  (repeat (1- nmeses)
    (setq datomen (substr datoexs (+ 9 (* (1- K) (+ 8 cary))) cary))
    (SETQ J (1+ K))
    (setq tpkendall 0)
    (setq bandera 0)
    (repeat (- nmeses k)
      (setq datomen2 (substr datoexs (+ 9 (* (1- J) (+ 8 cary))) cary))
      (if (= datomen datomen2)
        (progn
          (setq bandera2 0)
          (if (> k 1)
            (progn
              (setq cont3 1)
              (while (and (< cont3 k) (= bandera2 0))
                (setq datomen3 (substr datoexs (+ 9 (* (1- cont3) (+ 8 cary))) cary))
                (if (= datomen3 datomen2)
                  (setq bandera2 1)
                )
                (setq cont3 (1+ cont3))
              )
            )
          )
          (if (= bandera2 0)
            (if (= bandera 0)
              (progn
                (setq bandera 1)
                (setq gkendall (1+ gkendall))
                (setq tpkendall (1+ tpkendall))
              )
              (progn
                (setq bandera 1)
                (setq tpkendall (1+ tpkendall))
              )
            )
          )
        )
      )
      (IF (AND (/= DATOMEN CARACTERPROV) (/= DATOMEN2 CARACTERPROV))
        (PROGN
          (SETQ RESTA (- (ATOF DATOMEN2) (ATOF DATOMEN)))
          (IF (> RESTA 0) (SETQ SR 1))
          (IF (< RESTA 0) (SETQ SR -1))
          (IF (= RESTA 0) (SETQ SR 0))
        )
        (SETQ SR 0)
      )
      (setq srf (strcat srf "," (itoa sr) "h" DATOMEN "s" DATOMEN2))
      (SETQ S (+ S SR))
      (SETQ J (1+ J))
    )
    (if (> tpkendall 0) (setq htpkendall (strcat htpkendall (ntocad (1+ tpkendall) 0 3))))
    (SETQ K (1+ K))
  )
  (setq s s)   
)

(defun varianzas (datoexs)
  (setq nmeses (/ (strlen datoexs) (+ 8 cary)))
  (setq varpart1 (/ 1.00 18.00))
  (setq varpart2 (* nmeses (1- nmeses) (+ (* 2 nmeses) 5)))
  (setq contvrz 1)
  (setq varpart3 0)
  (repeat gkendall
    (setq vtp1 (atoi (substr htpkendall (1+ (* (1- contvrz) 3)) 3)))
    (setq varpart3 (+ varpart3 (* vtp1 (1- vtp1) (+ (* 2 vtp1) 5))))
    (setq contvrz (1+ contvrz)) 
  )
  (setq vars (* varpart1 (- varpart2 varpart3)))
)
