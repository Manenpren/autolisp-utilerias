Attribute VB_Name = "UserForm1"
Attribute VB_Base = "0{5ADCCD7B-6233-4E67-B2AA-9DCE98D01CE7}{ECB85A50-CEE2-4446-BFB0-4075860667B4}"
Attribute VB_GlobalNameSpace = False
Attribute VB_Creatable = False
Attribute VB_PredeclaredId = True
Attribute VB_Exposed = False
Attribute VB_TemplateDerived = False
Attribute VB_Customizable = False
Private Sub CommandButton1_Click()
   Dim g As Object
   Set g = GetObject()
   MsgBox$ g
End Sub
