(defun SUMA (punto xx yy)
  (setq x (car punto))
  (setq y (car (cdr punto)))
  (setq xxx (+ x xx))
  (setq yyy (+ y yy))
  (list xxx yyy)
)

(defun DatC (linea nudato)
  (setq cuen 0)
  (setq cuecom 0)
  (setq salir "N")
  (setq cadena "")
  (while (/= salir "S")
    (setq cuen (+ cuen 1))
    (setq caracter (substr linea cuen 1))
    (if (= caracter ",")
      (setq cuecom (+ cuecom 1))
    )
    (if (= cuecom (- nudato 1))
      (if (/= caracter ",")
        (setq cadena (strcat cadena caracter))
      )
    )
    (if (or (= cuecom nudato) (>= cuen (strlen linea)))
      (setq salir "S")
    )
  )
  (setq cadena cadena)
)


(defun c:CALAR2 ()
  (setq ent (car (entsel "Selecciona la linea de frontera: ")))
;  (setq pun (getpoint " Punto de control para desplazamiento de Offset: "))
  (setq ppun (getpoint " Punto en area para medición de superficies: "))
  (setq vertice (getpoint " Vertice en donde rotar : "))
  (if (= sep3 nil) (setq sep3 1))
  (setq sep2 (getreal (strcat " Separación de inicio: <" (rtos sep3) ">")))
  (if (/= sep2 nil) (progn (setq sep sep2) (setq sep3 sep2)) (setq sep sep3))
  (if (= are nil) (setq are 1))
  (setq are2 (getreal (strcat " Area a obtener: <" (rtos are) ">")))
  (if (/= are2 nil) (setq are are2))
  (setq por (getreal " Factor de presicion: <0.1> "))
  (if (not por)
    (setq por 0.1)
  )
  (setq incre sep)
  (setq arepol 0)
  (setq P 1)
  (while (/= (rtos are 2 4) (rtos arepol 2 4))
    (command "BPOLY" ppun "")
    (setq entpol (entlast))
    (command "AREA" "OB" entpol "")
    (setq arepol (getvar "AREA"))
    (setq AP  AU)
    (setq AU AREPOL)
    (if (< arepol are)
      (progn
;        (setq sep (+ sep incre))
        (setq fma 0)
      )
      (progn
        (setq sep (- sep incre))
        (setq fma 1)
      )
    )
    (if (= (rtos are 2 4) (rtos arepol 2 4))
      (write-line "Area localizada !!! ")
      (entdel entpol)
    )
    (if (/= fmaa fma)
      (setq incre (- incre (* incre 0.1)))
    )
    (if (= incre 0)
      (setq incre 0.3)
    )
    (setq fmaa fma)
    (if (= sep 0)
      (setq sep 0.01)
    )
    (if (< sep 0)
      (setq sep (* sep -1))
    )
    (setq sep2 (* SEP -1))
      (if (< ARE AU)
        (if (< ARE AP)
          (if (> AU AP)
            (setq P 2)
          )
        )
      )
    (if (/= (rtos are 2 4) (rtos arepol 2 4))
     (progn
      (if (= P 1)
        (if (= fma 0)
          (command "ROTATE" ENT "" VERTICE sep)
          (command "ROTATE" ENT "" VERTICE sep2)
        )
      )
      (if (= P 2)
        (if (= fma 0)
          (command "ROTATE" ENT "" VERTICE sep2)
          (command "ROTATE" ENT "" VERTICE sep)
        )
      )
     );progn
    );if
    (write-line (rtos incre 2 4))
  )
)
