;PROGRAMA PARA CALCULAR AREAS DE PREDIOS E INSERTAR NOMBRE DE PROPIETARIO
;SE REQUIERE CREAR UN BLOCK "NOMAR" CON ATRIBUTOS "NOMBRE" Y "AREA" CON
;ALTURA DE 1 Y CENTRADOS EN 0,0 NOMBRE SOBRE AREA
:CREAR PREVIO AL PROGRAMA EL LAYER "AREAS"
(DEFUN C:CA ()
     (SETQ N (GETINT "INICIO: "))
     (SETQ R1 N)
     (SETQ PROV "")
     (REPEAT 1000
       (SETQ XYZ (GETPOINT "DAME UN PUNTO AL CENTRO DEL AREA: "))
       (COMMAND "-BOUNDARY" XYZ "")
       (COMMAND "CHANGE" "L" "" "P" "LA" "AREAS" "")
       (COMMAND "AREA" "E" "L")
       (SETQ AP (RTOS (GETVAR "AREA") 2 3))
       (SETQ PROV (STRCAT "L" (ITOA R1)))
       (COMMAND "INSERT" (strcat ruta "blocks\\NOMAR") XYZ "" "" "" PROV AP)
       (SETQ R1 (1+ R1))
    )
)
