(defun c:p1 ()
  (COMMAND "SHELL" "dir c:\\arj\\curvas\\*.dwg > c:\\dir.txt /o:n")
  (setq ArcH (open "c:\\DIR.txt" "r"))
  (setq ArcH2 (open "c:\\BD.txt" "w"))
  (READ-LINE ARCH)
  (READ-LINE ARCH)
  (READ-LINE ARCH)
  (READ-LINE ARCH)
  (READ-LINE ARCH)
  (SETQ LIN (READ-LINE ARCH))
  (SETQ NARCH (SUBSTR LIN 1 8))
  (WRITE-LINE NARCH ARCH2)
  (WHILE LIN 
    (SETQ LIN (READ-LINE ARCH))
    (IF (= (SUBSTR LIN 1 1) " ")
      (SETQ LIN NIL)
    )
    (IF (/= LIN NIL)
      (PROGN
        (SETQ NARCH (SUBSTR LIN 1 8))
        (WRITE-LINE NARCH ARCH2)
      )
    )
  )
  (CLOSE ARCH)
  (CLOSE ARCH2)
)
