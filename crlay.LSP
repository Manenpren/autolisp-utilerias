(defun c:crla ()
        (command "undo" "M")
        (print "\n Creacion de layers")
        (setq s1 (getreal "\n Rango inferior de curvas : "))
        (setq s2 (getreal "\n Rango superior de curvas : "))
        (setq inc (getreal "\n Incremento : "))
        (setq rp (fix (/ (- s2 s1) inc)))
        (setq prov 0)
        (setq NCL 0)
        (repeat rp
          (setq prov (1+ prov))
          (setq NCL (1+ NCL))
          (if (= NCL 6)
            (setq NCL 1)
          )
          (setq NL (+ (* prov inc) s1))
          (SETQ NL (RTOS NL 2 3))
          (setq prov2 1)
          (while (/= "." (substr NL prov2 1))
            (setq prov2(1+ prov2))
          )
          (setq NL (strcat (substr NL 1 (1- prov2)) "-" (substr NL (1+ prov2) 3)))
          (command "layer" "M" NL "")
          (command "layer" "c" NCL NL "")
        )
)

(defun c:crlay2 ()
        (command "undo" "M")
        (print "\n Creacion de layers")
        (setq s1 (getreal "\n Rango inferior de curvas : "))
        (setq s2 (getreal "\n Rango superior de curvas : "))
        (setq inc (getreal "\n Incremento : "))
        (setq rp (fix (/ (- s2 s1) inc)))
        (setq prov 0)
        (setq NCL 2)
        (repeat rp
          (setq prov (1+ prov))
          (setq NCL (1+ NCL))
          (if (= NCL 6)
            (setq NCL 1)
          )
          (setq NL (+ (* prov inc) s1))
          (SETQ NL (RTOS NL 2 3))
          (setq prov2 1)
          (while (/= "." (substr NL prov2 1))
            (setq prov2(1+ prov2))
          )
          (setq NL (substr NL 1 (1- prov2))) 
          (command "layer" "M" NL "")
          (command "layer" "c" NCL NL "")
        )
)

(defun c:CHCUR ()
;  (IF (= (TYPE INICIO) REAL) (SETQ INICIO (ATOI (RTOS INICIO 2 0))))
;  (IF (= (TYPE INC) REAL) (SETQ INC (ATOI (RTOS INC 2 0))))
  (IF (= INICIO NIL) (SETQ INICIO 0))
  (SETQ INI (GETINT (STRCAT "\n INICIO DE CURVA <" (ITOA INICIO) "> :")))
  (IF (/= INI NIL) (SETQ INICIO INI))
  (setq inc2 (getINT (STRCAT "\n Incremento <" (ITOA INC) "> :")))
  (IF (/= INC2 NIL) (SETQ INC INC2))
  (PROMPT (STRCAT "SELECCIONA LOS OBJETOS DE LA CAPA " (ITOA INICIO)))
  (SETQ OBJ (SSGET))
  (WHILE OBJ
    (COMMAND "CHANGE" OBJ "" "P" "LAYER" INICIO "")
    (SETQ INICIO (+ INICIO INC))
    (PROMPT (STRCAT "SELECCIONA LOS OBJETOS DE LA CAPA " (ITOA INICIO)))
    (SETQ OBJ (SSGET))
  )
)
