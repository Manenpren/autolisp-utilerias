(defun verticeSURF (poli nov)
  (C:LIBRERIA "BUSCA VALOR DE ATRIBUTO")
  (setq listap (entget poli))
  (setq nver 0)
  (setq salir "N")
  (while (= salir "N")
    (setq sublisp (car listap))
    (if (= 10 (car sublisp))
      (progn
        (setq punto (cdr sublisp))   
        (setq nver (+ nver 1))
      )
    )
    (setq listap (cdr listap))
    (if listap
      (setq salir "N")
      (setq salir "S")
    )
    (if (= nov nver)
      (setq salir "S")
    )
  )
  (if (not listap)
    (setq punto nil)
  )
  (setq punto punto)
)

(DEFUN C:PERFSURF1 ()
  (setq lin (car (entsel "\n Selecciona la polylinea a procesar: ")))
  (SETQ ARRANQUE 1000)
  (while (/= "LWPOLYLINE" (cdr (assoc 0 (entget lin))))
      (if (/= "LWPOLYLINE" (cdr (assoc 0 (entget lin))))
        (progn   
          (alert "\nEl objeto debe ser polylinea ")
          (setq lin (car (entsel "\n Selecciona objeto: ")))
        )
      )
  )
  (setq arcdes "C:\\PERF.BLN")
    (setq f 0)
    (SETQ VER "")
    (while ver
       (setq f (1+ f))
       (SETQ VER (verticeSURF lin f)) 
    )
    (setq f (1- f))
    (SETQ f1 (OPEN arcdes "w"))
    (WRITE-LINE (STRCAT (RTOS F 2 0) ", 0" ) F1)
    (setq J 0)
    (REPEAT F
       (setq J (1+ J))
       (PRINT J)
       (SETQ VER (verticeSURF lin J))
       (IF (/= VER NIL)
         (write-line (strcat (rtos (car ver) 2 3) "," (rtos (car (cdr ver)) 2 3)) F1)
       )
    )
  (CLOSE F1)
  (setq GRDFILE (getfiled "ARCHIVO GRID FUENTE" "C:\\TOPOGRAF\\" "GRD" 18))
  (SETQ FGRD (OPEN "C:\\LISPMSA\\GRD.GRI" "w"))
  (WRITE-LINE GRDFILE FGRD)
  (CLOSE FGRD)
  (COMMAND "SHELL" "C:\\SURFER6\\GSMAC32.EXE /X C:\\LISPMSA\\PERFS.BAS")
;  (COMMAND "SHELL" "C:\\LISPMSA\\SEPARA.EXE")
  (LOAD (STRCAT RUTA "PERF"))
  (SETQ OPTPERF 1)
  (SETQ NOMARCH "C:\\PERF2.CSV")
  (C:CPO)
)

(DEFUN MPUN (POLI)
  (SETQ PROV 1)
  (SETQ P1T (VERTICESURF POLI PROV))
  (WHILE P1T
    (setq gpoLP (ssget "C" (suma p1T 0.10 0.10) (suma p1T -0.10 -0.10)))
    (SETQ R (sslength gpoLP))
    (SETQ PROV2 0)
    (setq mdist 100)
    (SETQ OBCOR NIL)
    (REPEAT R
      (SETQ OBJP (ssname gpoLP PROV2))
      (if (= "PUNTO" (cdr (assoc 2 (entget OBJP))))
       (progn
        (SETQ PVT (cdr (assoc 10 (entget OBJP))))
        (setq pdist (distance p1T pvT))
        (if (> mdist pdist)
         (progn
          (setq mdist pdist)
          (setq obcor objP)
         )
        )
       )
      )
      (SETQ PROV2 (1+ PROV2))
    )
    (if (AND (< 0 MDIST) (/= obcor nil))
      (PROGN
       (ALERT "HAY UN BLOCK FUERA DE SU POSICION")
       (SETQ XYZ (cdr (assoc 10 (ENTGET OBCOR))))
       (COMMAND "ZOOM" "C" XYZ "4")
       (COMMAND "CIRCLE" XYZ ".1")
       (SETQ PROVE (ENTLAST))
       (setQ OPT (GETSTRING "DESEAS MOVERLO HACIA LA LINEA (S/N) <S> :"))
       (IF (= "CIRCLE" (cdr (assoc 0 (ENTGET PROVE))))
         (COMMAND "ERASE" PROVE "")
       )
       (IF (= OPT "")
          (SETQ OPT "S") 
       )
       (IF (= OPT "S")
        (PROGN
         (command "MOVE" OBCOR "" (cdr (assoc 10 (entget OBCOR))) P1T)
        )
       )
       (COMMAND "ZOOM" "P")
      )
    )
    (SETQ PROV (1+ PROV))
    (SETQ P1T (VERTICESURF POLI PROV))
  )         
)

(DEFUN SUMA (P VX VY)
  (SETQ X (CAR P))
  (SETQ Y (CAR (CDR P)))
  (LIST (+ X VX) (+ Y VY) (LAST P))
)

(DEFUN EXLAYER (LAYBUS)
   (SETQ LAYPROV (tblnext "layer" T))
   (SETQ FIND "N")
   (WHILE LAYPROV
     (IF (= (cdr (assoc 2 LAYPROV)) LAYBUS)
       (PROGN
         (SETQ LAYPROV NIL)
         (SETQ FIND "S")
       )
       (SETQ LAYPROV (tblnext "layer"))
     )
   )
   (PRINT FIND)
)
