; busqueda.LSP

   ;  Û²±°   COMANDO   °±²Û
;  ³ BUSCA = BUSCA TEXTO ³

(defun checa ()
  (setq opc (OPEN "opc_busc.bus" "r"))
  (if opc
    (SETQ LIN (READ-LINE opc))
    (progn
      (setq opc (OPEN "opc_busc.bus" "w"))
      (write-line "todos" opc)
    )
  )
  (close opc)
  (setq opc (OPEN "nblock.bus" "r"))
  (if opc
    (SETQ LIN (READ-LINE opc))
    (progn
      (setq opc (OPEN "nblock.bus" "w"))
      (write-line "todos" opc)
    )
  )
  (close opc)
  (setq opc (OPEN "sblock.bus" "r"))
  (if opc
    (SETQ LIN (READ-LINE opc))
    (progn
      (setq opc (OPEN "sblock.bus" "w"))
      (write-line "todos" opc)
    )
  )
  (close opc)
  (setq opc (OPEN "layer.bus" "r"))
  (if opc
    (SETQ LIN (READ-LINE opc))
    (progn
      (setq opc (OPEN "layer.bus" "w"))
      (write-line "todos" opc)
    )
  )
  (close opc)
  (setq opc (OPEN "ftext.bus" "r"))
  (if opc
    (SETQ LIN (READ-LINE opc))
    (progn
      (setq opc (OPEN "ftext.bus" "w"))
      (write-line "todos" opc)
    )
  )
  (close opc)
  (setq opc (OPEN "stext.bus" "r"))
  (if opc
    (SETQ LIN (READ-LINE opc))
    (progn
      (setq opc (OPEN "stext.bus" "w"))
      (write-line "todos" opc)
    )
  )
  (close opc)
)  

(DEFUN BUSCA (CADENAB CADENAF CRIT)
  (SETQ LNG (STRLEN CADENAF))
  (SETQ LNG2 (STRLEN CADENAB))
  (SETQ PROV 0)
  (SETQ KL (1+ (- LNG LNG2)))
  (SETQ PS (STRCAT "*" CADENAB "*"))
  (IF (= CADENAB CADENAF)
    (PROGN
      (SETQ INICIO 1)
      (SETQ CRIT "V")
    ) 
  )
  (IF (and (WCMATCH CADENAF PS) (= crit ""))
    (PROGN
      (SETQ CRIT "V")
      (WHILE (< PROV KL)
        (SETQ PROV (1+ PROV))
        (SETQ PCAD (SUBSTR CADENAF PROV LNG2))
        (IF (= CADENAB PCAD)
          (PROGN
            (SETQ INICIO PROV)
            (SETQ PROV (1+ KL))
          ) 
        )
      )
    )
  )
  (IF (= crit "")
    (SETQ CRIT "F")
  )
  (PRINT CRIT)
)

(DEFUN BUSCAI (CADENAB CADENAF INICIO)
  (SETQ LNG (STRLEN CADENAF))
  (SETQ LNG2 (STRLEN CADENAB))
  (SETQ PROV 0)
  (SETQ KL (1+ (- LNG LNG2)))
  (SETQ PS (STRCAT "*" CADENAB "*"))
  (IF (= CADENAB CADENAF)
    (PROGN
      (SETQ INICIO 1)
      (SETQ CRIT "V")
    ) 
  )
  (IF (and (WCMATCH CADENAF PS) (= crit ""))
    (PROGN
      (SETQ CRIT "V")
      (WHILE (< PROV KL)
        (SETQ PROV (1+ PROV))
        (SETQ PCAD (SUBSTR CADENAF PROV LNG2))
        (IF (= CADENAB PCAD)
          (PROGN
            (SETQ INICIO PROV)
            (SETQ PROV (1+ KL))
          ) 
        )
      )
    )
  )
  (IF (= crit "")
    (SETQ CRIT "F")
  )
  (PRINT INICIO)
)

(DEFUN ACCION (INICIO CADENAB E OP SB)
  (setq XYZ (cdr (assoc 10 (entget E))))
  (IF (= "TEXT" (cdr (assoc 0 (entget E))))
    (PROGN
      (setq fs (cdr (assoc 40 (entget e))))
      (setq NOMBRE (cdr (assoc 1 (entget e))))
    )
    (PROGN
      (setq fs (cdr (assoc 41 (entget e))))
      (setq NOMBRE (cdr (assoc 2 (entget e))))
    )
  )
  (IF (= SB 0) (SETQ SB 1))
  (SETQ FS (* FS SB))
  (SETQ FS (/ FS 2))
  (SETQ LNGTEXT (* FS (STRLEN NOMBRE)))
  (SETQ X (CAR XYZ))
  (SETQ Y (CADR XYZ))
  (SETQ FX (FIX (+ X LNGTEXT)))
  (SETQ FY (FIX (+ Y FS)))
  (SETQ FXZ (STRCAT (ITOA FX) "," (ITOA FY)))
  (COMMAND "RECTANGLE" XYZ FXZ)
  (SETQ GP (SSGET "L"))
  (COMMAND "CHANGE" GP "" "P" "C" "RED" "")
  (setq OPBUS (getstring "\n Zoom/Remplazar/Siguiente/Anterior/saLir/ <Z>:"))
  (COMMAND "ERASE" GP "")
  (if (= OPBUS "")
    (SETQ OPBUS "Z")
  )
  (if (= (strcase OPBUS) "Z")
    (progn
      (SETQ ZXYZ (STRCAT (ITOA (FIX (+ (/ (ABS (- X FX)) 2) X))) ", " (ITOA (FIX (+ (/ (ABS (- Y FY)) 2) Y)))))
      (command "ZOOM" "C" ZXYZ (* (* LNGTEXT FS) 1))
    )
  )
  (if (= (strcase OPBUS) "S")
    (SETQ OP "S")
  )
  (if (= (strcase OPBUS) "R")
    (if (= "ATTRIB" (cdr (assoc 0 (entget E))))
     (progn
      (SETQ REP (GETSTRING "\n TEXTO A REMPLAZAR :"))
      (setq NOMBRE (cdr (assoc 2 (entget e))))
      (SETQ LNG (STRLEN CADENAB))
      (SETQ LNG2 (STRLEN NOMBRE))
      (SETQ LNG (1- (+ INICIO LNG)))
      (SETQ P1 (- INICIO 1))
      (SETQ P2 (1+ (- LNG2 LNG)))
      (IF (< P1 0)
        (SETQ P1 (* P1 -1))
      )
      (IF (< P2 0)
        (SETQ P2 (* P2 -1))
      )
      (SETQ REMPLAZO (STRCAT (SUBSTR NOMBRE 1 P1) REP (SUBSTR NOMBRE LNG P2)))
      (COMMAND "attedit" "" "" "" "" E "V" "R" REMPLAZO "")
     )
     (progn
      (SETQ REP (GETSTRING "\n TEXTO A REMPLAZAR :"))
      (setq NOMBRE (cdr (assoc 1 (entget e))))
      (SETQ LNG (STRLEN CADENAB))
      (SETQ LNG2 (STRLEN NOMBRE))
      (SETQ LNG (1+ (+ INICIO LNG)))
      (SETQ P1 (- INICIO 1))
      (SETQ P2 (- LNG2 LNG))
      (IF (< P1 0)
        (SETQ P1 (* P1 -1))
      )
      (IF (< P2 0)
        (SETQ P2 (* P2 -1))
      )
      (SETQ REMPLAZO (STRCAT (SUBSTR NOMBRE 1 P1) REP (SUBSTR NOMBRE LNG P2)))
      (COMMAND "CHANGE" E "" "" "" "" "" "" REMPLAZO)
     )
    )
  )
  (if (= (strcase OPBUS) "L")
    (COMMAND ^c)
  )
)

(defun NUMEROS (NNBLOCK NSBLOCK NLAYER NSTEXT NFTEXT)
  (checa)
  (setq opc (OPEN "opc_busc.bus" "r"))
  (SETQ LIN (READ-LINE opc))
  (close opc)
(if (= LIN "todos")
  (setq opcbus "todos")
  (progn
    (setq opcbus "opciones")
    (SETQ NNBLOCK 0)
    (setq opc (OPEN "nblock.bus" "r"))
    (SETQ LIN (READ-LINE opc))
    (if (= lin "todos")
      (progn
        (setq opcNBLOCK "todos")
        (close opc)
      )
      (progn
        (while (/= LIN "")
          (SETQ NNBLOCK(1+ NNBLOCK))
          (SETQ LIN (READ-LINE opc))
        )
        (close opc)
      )
    )
    (SETQ NSBLOCK 0)
    (setq opc (OPEN "Sblock.bus" "r"))
    (SETQ LIN (READ-LINE opc))
    (if (= lin "todos")
      (progn
        (setq opcSBLOCK "todos")
        (close opc)
      )
      (progn
        (while (/= LIN "")
          (SETQ NSBLOCK(1+ NSBLOCK))
          (SETQ LIN (READ-LINE opc))
        )
        (close opc)
      )
    )
    (SETQ NLAYER 0)
    (setq opc (OPEN "LAYER.bus" "r"))
    (SETQ LIN (READ-LINE opc))
    (if (= lin "todos")
      (progn
        (setq opcLAYER "todos")
        (close opc)
      )
      (progn
        (while (/= LIN "")
          (SETQ NLAYER (1+ NLAYER))
          (SETQ LIN (READ-LINE opc))
        )
        (close opc)
      )
    )
    (SETQ FTEXT 0)
    (setq opc (OPEN "FTEXT.bus" "r"))
    (SETQ LIN (READ-LINE opc))
    (if (= lin "todos")
      (progn
        (setq opcFTEXT "todos")
        (close opc)
      )
      (progn
        (while (/= LIN "")
          (SETQ NFTEXT (1+ NFTEXT))
          (SETQ LIN (READ-LINE opc))
        )
        (close opc)
      )
    )
    (SETQ STEXT 0)
    (setq opc (OPEN "STEXT.bus" "r"))
    (SETQ LIN (READ-LINE opc))
    (if (= lin "todos")
      (progn
        (setq opcSTEXT "todos")
        (close opc)
      )
      (progn
        (while (/= LIN "")
          (SETQ NSTEXT (1+ NSTEXT))
          (SETQ LIN (READ-LINE opc))
        )
        (close opc)
      )
    )
  )
)
)

(defun C:BUSCA ()
  (busqueda2)
)

(defun BUSQUEDA2 ()
  (setq NNBLOCK 0)
  (setq NSBLOCK 0)
  (setq NLAYER 0)
  (setq NSTEXT 0)
  (setq NFTEXT 0)
  (NUMEROS NNBLOCK NSBLOCK NLAYER NSTEXT NFTEXT)
  (print "\n Busqueda de texto inteligente ")
  (setq BUSQ (getstring "\n TEXTO A BUSCAR :"))
  (setq E (entnext))
  (SETQ OPCBUS "TODOS")
  (IF (= OPCBUS "TODOS")
    (progn
      (while E
         (if (= "INSERT" (cdr (assoc 0 (entget E))))
            (PROGN
              (SETQ SB (cdr (assoc 41 (entget E))))
              (SETQ E (ENTNEXT E))
            (WHILE (= "ATTRIB" (cdr (assoc 0 (entget E))))
             (if (= "ATTRIB" (cdr (assoc 0 (entget E))))
              (progn
                (setq NOMBRE (cdr (assoc 1 (entget E))))
                (SETQ CADENAB BUSQ)
                (SETQ CADENAF NOMBRE)
                (SETQ CRIT "")
                (SETQ INICIO 0)
                (SETQ CRIT (BUSCA CADENAB CADENAF CRIT))
                (SETQ INICIO(BUSCAI CADENAB CADENAF INICIO))
                (IF (= CRIT "V")
                  (ACCION INICIO CADENAB E OP SB)    
                )
              )
             )
             (SETQ E (ENTNEXT E))
            )
            )
         )
         (if (= "TEXT" (cdr (assoc 0 (entget E))))
           (progn
             (setq NOMBRE (cdr (assoc 1 (entget E))))
             (SETQ SB 1)
             (SETQ CADENAB BUSQ)
             (SETQ CADENAF NOMBRE)
             (SETQ CRIT "")
             (SETQ INICIO 0)
             (SETQ CRIT (BUSCA CADENAB CADENAF CRIT))
             (SETQ INICIO (BUSCAI CADENAB CADENAF INICIO))
             (IF (= CRIT "V")
               (ACCION INICIO CADENAB E OP SB)    
             )
           )
         )
         (setq E (entnext E))
      )
    )
  )
)
