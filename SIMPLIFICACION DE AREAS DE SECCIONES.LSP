(DEFUN C:SIMAR ()
  (C:LIBRERIA "SEARCH OBJ GPO")
  (C:LIBRERIA "BUSCA VALOR DE ATRIBUTO")
  (C:LIBRERIA "AREA OBTENIDA EN UN PUNTO")
  (C:LIBRERIA "ASOCIASIONES")
  (COMMAND "UNDO" "M")
  (COMMAND "VIEW" "S" "C")
  (setq PROV (CAR (ENTSEL "SELECCIONA BLOCK")))
  (setq NOMBLO (cdr (assoc 2 (entget PROV))))
  (COMMAND "INSERT" NOMBLO "0,0" "" "" "")
  (SETQ X (ENTLAST))
  (COMMAND "EXPLODE" X "")
  (SETQ GPOA (SSGET "P"))
  (SETQ P 0)
  (WHILE (/= (cdr (assoc 0 (entget PROV))) "TEXT")
    (SETQ PROV (SSNAME GPOA P))
    (SETQ P (1+ P))
  )
  (setq XY (cdr (assoc 10 (entget PROV))))
  (command "layer" "fr" "tn" "")
  (SETQ Y (CADR XY))
  (SETQ XY (STRCAT "0," (RTOS Y)))
  (COMMAND "ZOOM" "C" XY "25")
  (C:1)
  (SETQ AREACORTE 0)
  (SETQ AFI 0)
  (SETQ ABA 0)
  (SETQ ACA 0)
  (SETQ ABN 0)
;  (WHILE (/= NOMBRE "CORTE")
;    (SETQ NOBJ (S_OBJ_GPO GPO NINICIO 2 "NOMAR" OBR)) 
;    (SETQ PROV (SSNAME GPOA NOBJ))
;    (SETQ NOMBRE (BUSATR PROV "NOMBRE"))
;    (SETQ NINICIO (1+ OBR))
;  )
;  (SETQ AREACORTE (BUSATR PROV "AREA"))
;  (COMMAND "ERASE" PROV "")
  (SETQ CORTE (CAR (ENTSEL "SELECCIONA BLOCK DE CORTE")))
  (SETQ AREACORTE (BUSATR CORTE "AREA"))  
  (COMMAND "ERASE" CORTE "")
  (setq ELPROY (CAR (ENTSEL "SELECCIONA EL TEXTO DE ELEVACION DE PROYECTO")))
  (SETQ ELEBASE (ATOF (cdr (assoc 1 (entget ELPROY)))))
  (SETQ PCA (LIST 0.0 (- ELEBASE 0.025) 0.0))
  (SETQ PBA (LIST 0.0 (- ELEBASE 0.15) 0.0))
  (SETQ PFI (LIST 0.0 (- ELEBASE 0.30) 0.0))
;  (SETQ PFI (GETPOINT "DAME UN PUNTO EN MEDIO DEL AREA DE /FILTRO/ ")) 
  (SETQ AFI (AREAP PFI AFI))
;  (SETQ PBA (GETPOINT "DAME UN PUNTO EN MEDIO DEL AREA DE LA /BASE/ "))
  (SETQ ABA (AREAP PBA ABA))
;  (SETQ PCA (GETPOINT "DAME UN PUNTO EN MEDIO DEL AREA DE LA /CARPETA/ "))
  (SETQ ACA (AREAP PCA ACA))
  (SETQ OP (strcase (GETSTRING "TU SECCION TIENE BANQUETAS (S/N) <N> ")))
  (IF (= OP NIL) (OP "N"))
  (IF (= OP "S")
   (PROGN
    (SETQ OP (GETSTRING "UNA O DOS BANQUETAS (1/2) ")) 
    (IF (= OP "1")
      (PROGN
        (SETQ PBN (GETPOINT "DAME UN PUNTO EN MEDIO DEL AREA DE LA /BANQUETA/ "))
        (COMMAND "-BOUNDARY" PBN "")
        (COMMAND "AREA" "E" "L" "ERASE" "L" "")
        (SETQ ABN (RTOS (GETVAR "AREA") 2 3))
      )
      (PROGN
        (SETQ PBN (GETPOINT "DAME UN PUNTO EN MEDIO DEL AREA DE LA /BANQUETA/ "))
        (SETQ PBN2 (GETPOINT "DAME UN PUNTO EN MEDIO DEL AREA DE LA /BANQUETA2/ "))
        (COMMAND "-BOUNDARY" PBN "")
        (COMMAND "AREA" "E" "L" "ERASE" "L" "")
        (SETQ ABN1 (GETVAR "AREA"))
        (COMMAND "-BOUNDARY" PBN2 "")
        (COMMAND "AREA" "E" "L" "ERASE" "L" "")
        (SETQ ABN2 (GETVAR "AREA"))
        (SETQ ABN (RTOS (+ ABN1 ABN2) 2 3))
      )
    )
   )
  )
  (C:2)
  (COMMAND "ZOOM" "C" XY "25")
  (SETQ PINS (GETPOINT "DAME EL PUNTO DE INSERCION DE LAS AREAS "))
  (COMMAND "INSERT" "AREAS" PINS ".15" "" "" "1" "1" "1" "1" "1" "" "" "" "" "")
; AREACORTE AFI ABA ACA ABN
  (SSADD (ENTLAST) GPOA)
  (setq bl (entnext (ENTLAST)))
  (COMMAND "attedit" "" "" "" "" bl "V" "R" AREACORTE "")
  (setq bl (entnext BL))
  (COMMAND "attedit" "" "" "" "" bl "V" "R" AFI "")
  (setq bl (entnext BL))
  (COMMAND "attedit" "" "" "" "" bl "V" "R" ABA "")
  (setq bl (entnext BL))
  (COMMAND "attedit" "" "" "" "" bl "V" "R" ACA "")
  (setq bl (entnext BL))
  (COMMAND "attedit" "" "" "" "" bl "V" "R" ABN "")
  (command "layer" "th" "tn" "")
  (COMMAND "BLOCK" NOMBLO "Y" "0,0" GPOA "")
  (COMMAND "VIEW" "R" "C")

)
