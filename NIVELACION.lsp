(defun C:NIVELACION3 ()
  (C:LIBRERIA "BUSCA VALOR DE ATRIBUTO")
  (C:LIBRERIA "VERTICES DE UNA LWPOLYLINE")
  (C:LIBRERIA "BUSCA LAYER EN BASE DE DATOS")
  (setq cdrive (substr ruta 1 1))
  (PROMPt "CALCULO DE AREAS DE CORTES Y TERRAPLENES")
  (setq os (getvar "osmode"))
  (COMMAND "UNDO" "M")
  (command "OSNAP" "none")
  (SETQ OPPRV (BSLAYER "RET20X20"))
  (IF (/= OPPRV "S") (COMMAND "LAYER" "M" "RET20X20" "C" "RED" "" ""))
  (SETQ OPPRV (BSLAYER "RET20X20PR"))
  (IF (/= OPPRV "S") (COMMAND "LAYER" "M" "RET20X20PR" "C" "BLUE" "" ""))
  (SETQ OPPRV (BSLAYER "NIVTNF"))
  (IF (/= OPPRV "S") (COMMAND "LAYER" "M" "NIVTNF" "C" "GREEN" "" ""))
  (SETQ OPPRV (BSLAYER "NIVPRF"))
  (IF (/= OPPRV "S") (COMMAND "LAYER" "M" "NIVPRF" "C" "MAGENTA" "" ""))
  (SETQ GPOP (SSADD))                                                                               ;seleciona nomnum
  (SETQ GPOP (SSGET "X" '((2 . "NOMNUM"))))
  (IF (/= (SSLENGTH GPOP) 1)
   (PROGN
     (ALERT "hay dos blocks con attributos de nombre y numero de lote")
     (setq ex (car (entsel "Selecciona el block fuente" )))
   )
   (SETQ EX (SSNAME GPOP 0))
  )
  (setq pto (cdr (assoc 10 (entget Ex))))
  (command "move" "all" "" pto "0,0")
  (setq regreso pto)
  (setq pto (cdr (assoc 10 (entget Ex))))
  (command "zoom" "e")
  (PROMPt "SELECCIONA LOS BLOQUES DE NIVEL")
  (SETQ GPONIV (SSADD))
  (SETQ GPONIV (ssget "X" '((0 . "INSERT") (2 . "PUN2"))))
  (SETQ linea (CAR (ENTSEL "\n Selecciona la poligonal envolvente ")))
  (setq polenvolvente linea)
  (SETQ PROV 1)
  (SETQ P1T (VERTICE LINEA PROV))
  (SETQ XMENOR (CAR P1T))
  (SETQ YMENOR (CADR P1T))
  (SETQ XMAYOR XMENOR)
  (SETQ YMAYOR YMENOR)
  (SETQ PROVV P1T)
  (while p1t
    (SETQ X2PROV (CAR P1T))
    (SETQ Y2PROV (CADR P1T))
    (IF (AND (< X2PROV XMENOR) (/= X2PROV nil)) (SETQ XMENOR X2PROV))
    (IF (AND (< Y2PROV YMENOR) (/= Y2PROV nil)) (SETQ YMENOR Y2PROV))
    (IF (AND (> X2PROV XMAYOR) (/= X2PROV nil)) (SETQ XMAYOR X2PROV))
    (IF (AND (> Y2PROV YMAYOR) (/= Y2PROV nil)) (SETQ YMAYOR Y2PROV))
    (SETQ PROV (1+ PROV))
    (SETQ P1T (VERTICE LINEA PROV))
  )
  (COMMAND "ZOOM" "W" (STRCAT (RTOS XMENOR 2 6) "," (RTOS YMENOR 2 6)) (STRCAT (RTOS XMAYOR 2 6) "," (RTOS YMAYOR 2 6)))  
  (SETQ PROV (1- PROV))
  (SETQ ARCLINEA (OPEN "c:\\LINEA.CSV" "w"))
  (WRITE-LINE (STRCAT (ITOA PROV) ",0") ARCLINEA)
  (SETQ PROV 1)
  (SETQ P1T (VERTICE LINEA PROV))
  (SETQ PROVV P1T)
  (while p1t
    (SETQ X2PROV (CAR P1T))
    (SETQ Y2PROV (CADR P1T))
    (SETQ LAR (STRCAT (RTOS X2PROV 2 6) "," (RTOS Y2PROV 2 6)))
    (IF (AND (/= LAR "") (/= LAR NIL)) (WRITE-LINE LAR ARCLINEA))
    (SETQ PROV (1+ PROV))
    (SETQ P1T (VERTICE LINEA PROV))
  )
  (SETQ PROV 0)
  (CLOSE ARCLINEA)
;  (SETQ PTO (GETPOINT "\n Punto central del poligono "))
  (COMMAND "OFFSET" 3 linea pto "")
  (setq lprov (entlast))
;  (setq lprov LINEA)
  (SETQ X1 (VERTICE LPROV 1))
  (SETQ X2 (VERTICE LPROV 2))
  (SETQ X3 (VERTICE LPROV 3))
  (SETQ X4 (VERTICE LPROV 4))
  (IF (/= X4 NIL)
   (PROGN
    (IF (AND (< (DISTANCE X1 X2) (DISTANCE X2 X3)) (> (DISTANCE X2 X3) (DISTANCE X3 X4)) (> (DISTANCE X3 X4) (DISTANCE X4 X1)))
      (PROGN 
        (SETQ X1 X2)
        (SETQ X2 X3)
      )
    )
    (IF (AND (< (DISTANCE X1 X2) (DISTANCE X2 X3)) (< (DISTANCE X2 X3) (DISTANCE X3 X4)) (> (DISTANCE X3 X4) (DISTANCE X4 X1)))
      (PROGN
        (SETQ X1 X3)
        (SETQ X2 X4)
       )
    )
    (IF (AND (< (DISTANCE X1 X2) (DISTANCE X2 X3)) (< (DISTANCE X2 X3) (DISTANCE X3 X4)) (< (DISTANCE X3 X4) (DISTANCE X4 X1)))
       (PROGN
        (SETQ X1 X4)
        (SETQ X2 X1)
       )
    )
   )
   (PROGN
    (setq x1RET x2)
    (setq x2RET x3)
   )
  ) 
  (setq x1RET x1)
  (setq x2RET x2)
  (command "erase" lprov "")
  (COMMAND "ATTDISP" "OFF" "PDMODE" "0" )
  (command "insert" (strcat ruta "BLOCKS\\reticula.dwg") X1 "" "" X2)
  (setq ret (entlast))
  (COMMAND "EXPLODE" RET "")
  (SETQ GPORET (SSADD))
  (SETQ GPORET (SSGET "P"))
  (COMMAND "CHANGE" GPORET "" "P" "LA" "RET20X20" "")
  (SETQ PROV 1)
  (SETQ VER1 (VERTICE LINEA prov))
  (COMMAND "ERASE" GPORET "R" "CP")
  (WHILE VER1
     (IF (/= VER1 NIL)
      (progn
        (SETQ Y (CADR ver1))
        (SETQ Y (RTOS Y 2 3))
        (SETQ X (CAR ver1))
        (SETQ X (RTOS X 2 3))
        (COMMAND (STRCAT X "," Y))
      )
      (COMMAND "")
     )
     (SETQ PROV (1+ PROV))
     (SETQ VER1 (vertice LINEA prov))
  )
  (command "" "")
  (SETQ PE (GETPOINT "\n PUNTO EXTERIOR PARA LIMPIAR LAS CURVAS "))
  (COMMAND "OFFSET" "60" LINEA PE "")
  (setq LINEA2 (entlast))
  (SETQ PROV 1)
  (SETQ P1T (VERTICE LINEA2 PROV))
  (SETQ XMENOR (CAR P1T))
  (SETQ YMENOR (CADR P1T))
  (SETQ XMAYOR XMENOR)
  (SETQ YMAYOR YMENOR)
  (SETQ PROVV P1T)
  (while p1t
    (SETQ X2PROV (CAR P1T))
    (SETQ Y2PROV (CADR P1T))
    (IF (AND (< X2PROV XMENOR) (/= X2PROV nil)) (SETQ XMENOR X2PROV))
    (IF (AND (< Y2PROV YMENOR) (/= Y2PROV nil)) (SETQ YMENOR Y2PROV))
    (IF (AND (> X2PROV XMAYOR) (/= X2PROV nil)) (SETQ XMAYOR X2PROV))
    (IF (AND (> Y2PROV YMAYOR) (/= Y2PROV nil)) (SETQ YMAYOR Y2PROV))
    (SETQ PROV (1+ PROV))
    (SETQ P1T (VERTICE LINEA2 PROV))
  )
  (SETQ PROV 0)
  (COMMAND "ZOOM" "W" (STRCAT (RTOS XMENOR 2 6) "," (RTOS YMENOR 2 6)) (STRCAT (RTOS XMAYOR 2 6) "," (RTOS YMAYOR 2 6)) "" "")  
  (setq filexyz (open "c:\\xylim.xyz" "w"))
  (WRITE-LINE (rtos XMenor 2 6) FILEXYZ)
  (WRITE-LINE (rtos YMenor 2 6) FILEXYZ)
  (WRITE-LINE (rtos XMAyor 2 6) FILEXYZ)
  (WRITE-LINE (rtos YMAyor 2 6) FILEXYZ)
  (CLOSE FILEXYZ)
  (COMMAND "ATTDISP" "ON" "PDMODE" "3" )
  (command "erasE" linea2 "")
  (SETQ GPORET (SSADD))
  (SETQ GPORET (SSGET "X" '((8 . "RET20X20"))))
  (setq ArcDES (open "c:\\TOPOGRAF\\BLN.TMP" "w"))
  (setq e (ssname gpoRET 0))
  (setq conta 1)
  (while e
    (SETQ LINEA "")
    (if (= (cdr (assoc 0 (entget E))) "POINT")
      (PROGN
        (SETQ PUNTO (cdr (assoc 10 (entget E))))
        (SETQ X (CAR PUNTO))
        (SETQ X (RTOS X 2 5))
        (SETQ Y (CADR PUNTO))
        (SETQ Y (RTOS Y 2 5))
        (SETQ LINEA (STRCAT X "," Y))
      )
    )
    (IF (/= LINEA "")
       (WRITE-LINE LINEA ARCDES)
    )
    (setq e (ssname gpoRET conta))
    (setq conta (1+ conta))
  )
  (SETQ CONTA (1- CONTA))
  (CLOSE ARCDES)
  (setq ArcDES (open "c:\\TOPOGRAF\\BLN.CSV" "w"))
  (setq ArcL (open "c:\\TOPOGRAF\\BLN.TMP" "r"))
  (WRITE-LINE (STRCAT (ITOA CONTA) ", 0" ) ARCDES)
  (SETQ LNINPUT (READ-LINE arcL))
  (WHILE LNINPUT
    (IF (AND (/= LNINPUT nil) (/= LNINPUT "")) (WRITE-LINE LNINPUT ARCDES))
    (SETQ LNINPUT (READ-LINE arcL))
  )
  (CLOSE ARCDES)
  (CLOSE ARCL)
  (setq e (ssname gponiv 0))
  (setq conta 1)
  (setq ArcDES (open "c:\\TOPOGRAF\\PROV.CSV" "w"))
  (while e
    (SETQ LINEA "")
    (if (= (cdr (assoc 0 (entget E))) "INSERT")
      (PROGN
        (SETQ ELEVA (BUSATR E "ELEV"))
        (if (/= eleva nil)
         (progn
          (SETQ CODIG (BUSATR E "CODE"))
          (SETQ PUNTO (cdr (assoc 10 (entget E))))
          (SETQ X (CAR PUNTO))
          (SETQ X (RTOS X 2 5))
          (SETQ Y (CADR PUNTO))
          (SETQ Y (RTOS Y 2 5))
          (SETQ LINEA (STRCAT X "," Y "," ELEVA "," (ITOA CONTA)  "," CODIG))
         )
        )
      )
    )
    (IF (/= LINEA "")
       (WRITE-LINE LINEA ARCDES)
    )
    (setq e (ssname gponiv conta))
    (setq conta (1+ conta))
  )
  (CLOSE ARCDES)
  (COMMAND "SHELL" (strcat cdrive ":\\SURFER6\\GSMAC32.EXE /X " RUTA "NIVLOT.BAS"))
  (setq archC (OPEN "C:\\TEMP.TMP" "w"))
  (WRITE-LINE "N" ARCHC)
  (CLOSE ARCHC)
  (setq lprov "N")
  (WHILE (/= LPROV "S")
    (setq archc nil)
    (WHILE (= ARCHC NIL)
      (COMMAND "DELAY" "5000")
      (setq archC (OPEN "C:\\TEMP.TMP" "r"))
    )
    (setq LPROV (READ-LINE ARCHC))
    (print lprov)
    (CLOSE ARCHC)
  )
  (COMMAND "REGENALL")
  (setq ex 1.13)
  (setq ey 1.13) 
  (COMMAND "INSERT" (STRCAT RUTA "BLOCKS\\PUN2") (list ex ey) ".1" "" "" "" "" "" "" "" "" "")
  (SETQ UL (ENTLAST))
  (COMMAND "CHANGE" UL "" "P" "LA" "NIVTNF" "")
  (SETQ OPINSAT 0)
  (load (strcat ruta "INSATR"))
  (SETQ Nomblo "PUN2")
  (SETQ tt 1.00)
  (SETQ NOMARCH "C:\\PERF2.CSV")
  (SETQ Ini 1)
  (SETQ Fin 30000)
  (SETQ tri "2")
  (setq lisblo (tblsearch "block" nomblo))
  (ABLOQUE)
  (setq arch (OPEN nomarch "r"))
  (if arch
    (LEE)
    (print "\n Archivo no encontrado ")
  )
  (close arch)
  (setq arch (OPEN NOMARCH "r"))
  (if arch
    (LEE2)
  )
  (close arch)
  (entdel ul)
  (SETQ OPINSAT 1)
  (SETQ GPORTN (SSADD))
  (SETQ GPORTN (SSGET "X" '((8 . "NIVTNF"))))
  (COMMAND "ERASE" GPORTN "R")
  (SETQ PROV 0)
  (SETQ E (SSNAME GPORET prov))
  (SETQ X2 0.0)
  (SETQ Y2 0.0)
  (WHILE E
    (if (= (cdr (assoc 0 (entget E))) "POINT")
      (PROGN
        (SETQ PUNTO (cdr (assoc 10 (entget E))))
        (SETQ X (+ 0.0001 (CAR PUNTO)))
        (SETQ X (RTOS X 2 6))
        (SETQ Y (+ 0.0001 (CADR PUNTO)))
        (SETQ Y (RTOS Y 2 6))
        (SETQ X2 (- (CAR PUNTO) 0.0000001))
        (SETQ X2 (RTOS X2 2 6))
        (SETQ Y2 (- (CADR PUNTO) 0.0000001))
        (SETQ Y2 (RTOS Y2 2 6))
        (SETQ LINEA (STRCAT X "," Y ",0"))
        (SETQ LINEA2 (STRCAT X2 "," Y2 ",0"))
        (COMMAND "C" LINEA LINEA2)
      )
    )
    (setq PROV (1+ PROV))
    (setq e (ssname gpoRET PROV))
  )
  (COMMAND "" "")
  (SETQ OPPRV (BSLAYER "CURVASTN"))
  (IF (/= OPPRV "S") (COMMAND "LAYER" "M" "CURVASTN" "C" "GREEN" "" ""))
  (COMMAND "DXFIN" "C:\\NIVLOT.DXF")
  (SETQ GPOCURVAS (SSGET "X" '((8 . "GSLAYER"))))
  (COMMAND "CHANGE" GPOCURVAS "" "P" "LA" "CURVASTN" "")
  (SETQ VLIMPIA 1)
  (SETQ e polenvolvente)
  (SETQ LAYCONG "CURVASTN")
  (if (= (getvar "acadver") "14.0")
    (progn
      (LOAD (STRCAT RUTA "LIMPIA14"))
      (C:LIMPI)
    )
    (progn
      (command "expresstools")
      (LOAD (STRCAT RUTA "LIMPIA"))
      (SETQ na E)
      (SETQ P1 PE)
      (C:LIMPI)
    )
  )
  (SETQ VLIMPIA 0)
  (CONTINUANIV)
)

(defun SUMA (punto xx yy)
  (setq x (car punto))
  (setq y (car (cdr punto)))
  (setq xxx (+ x xx))
  (setq yyy (+ y yy))
  (list xxx yyy)
)

(DEFUN CONTINUANIV ()
;  (SETQ pbase (CAR (ENTSEL "\n Selecciona el block de elevacion que sera la base de la reticula final ")))
  (setq gpohi (ssget "_W" '(20 20) '(-20 -20)))
  (SETQ CONTHI 0)
  (SETQ XXX 1)
  (WHILE XXX
   (setq PBASE (ssname gpohi CONTHI))
   (IF (= "PUN2" (cdr (assoc 2 (entget pbase))))
     (IF (= "NIVTNF" (cdr (assoc 8 (entget pbase))))
       (PROGN  
         (SETQ XXX NIL)
       )
     )
   )
   (SETQ CONTHI (1+ CONTHI))
  )
  (SETQ ELEVACION (BUSATR PBASE "ELEV"))
  (SETQ PUNTO2 (cdr (assoc 10 (entget pbase))))
;  (SETQ PENDIENTE (GETREAL "\n DAME LA PENDIENTE FINAL DEL TERRENO (1.00 = 100%) :"))
  (SETQ PENDIENTE 0)
  (IF (/= PENDIENTE 0)
    (SETQ PTO2 (GETPOINT "\n Direccion de la reticula de proyecto "))
  )
  (IF (= PENDIENTE 0)
    (pendiente1)
    (pendiente2)
  )                                                                                                   ;COMIENZO DE IF PENDIENTE1
  (setq gpor20 (ssget "x" '((8 . "RET20X20"))))
  (command "erase" gpor20 "")
;  (setq gpor20 (ssget "x" '((8 . "RET20X20PR"))))
;  (command "erase" gpor20 "")
  (COMMAND "REGENALL")
  (setvar "osmode" os)
  (COMMAND "ZOOM" "e")
  (COMMAND "QSAVE" "CLOSE")
)

(defun pendiente2 ()
  (command "insert" (strcat ruta "BLOCKS\\FLECHApen.dwg") punto2 "0.3" "" pto2 "" "" "")
  (command "MOVE" (ENTLAST) "" PUNTO2 PTO2)
  (setq blc (entlast))
  (setq blc (entnext blc))
  (COMMAND "attedit" "" "" "" "" blc "V" "R" (strcat (rtos (* pendiente 100) 2 2) " %") "")
  (command "insert" (strcat ruta "BLOCKS\\reticulap.dwg") punto2 "" "" pto2)
  (setq ret (entlast))
  (COMMAND "EXPLODE" RET "")
  (SETQ GPORET (SSADD))
  (SETQ GPORET (SSGET "P"))
  (COMMAND "CHANGE" GPORET "" "P" "LA" "RET20X20PR" "")
  (COMMAND "OFFSET" "60" POLENVOLVENTE PE "")
  (setq LINEA2 (entlast))
  (SETQ GPORPR (SSADD))
  (SETQ GPORPR (SSGET "X" '((8 . "RET20X20PR"))))
  (SETQ PROV 1)
  (SETQ 2DALINEA LINEA2)
  (SETQ VER1 (VERTICE LINEA2 prov))
  (COMMAND "ERASE" GPORPR "R" "CP")
  (WHILE VER1
     (IF (/= VER1 NIL)
      (progn
        (SETQ Y (CADR ver1))
        (SETQ Y (RTOS Y 2 3))
        (SETQ X (CAR ver1))
        (SETQ X (RTOS X 2 3))
        (COMMAND (STRCAT X "," Y))
      )
      (COMMAND "")
     )
     (SETQ PROV (1+ PROV))
     (SETQ VER1 (vertice LINEA2 prov))
  )
  (command "" "")
  (command "erase" linea2 "")
  (setq p1 (suma punto2 0.05 0.05))
  (setq p2 (suma punto2 -0.05 -0.05))
  (SETQ GPOPROV2 (SSADD))
  (setq Gpoprov2 (ssget "C" p1 p2))
  (setq prov 0)
  (setq e (ssname gpoprov2 prov))
  (while e
    (if (= (STRCASE (cdr (assoc 8 (entget e)))) "NIVTNF")
        (SETQ ELEVATN (BUSATR E "ELEV"))
    )
    (if (= (STRCASE (cdr (assoc 8 (entget e)))) "RET20X20PR")
      (PROGN
        (SETQ PUNTOPR (BUSATR E "PUNTO"))
        (SETQ BL E)
      )
    )
    (setq prov (1+ PROV))
    (setq e (ssname gpoprov2 prov))
  )
  (setq vcorte "1")
  (setq vterrap "2")
  (setq vsuma 1)
  (setq opcorte 0)
  (setq bl (entnext BL))
  (setq bl (entnext BL))
  (SETQ ARCHSVOL (OPEN "C:\\VOL.TMP" "w"))
  (CLOSE ARCHSVOL)   
  (SETQ VRETORNO 0)
  (SETQ VRETORNO2 0)
; (while (and (/= (RTOS (ATOF vcorte) 2 1) (RTOS (ATOF vterrap) 2 1)) (/= elevg2 elevg1 elevatn))
  (COMMAND "attedit" "" "" "" "" bl "V" "R" ELEVATN "")
  (SETQ GPORPR (SSADD))
  (SETQ GPORPR (SSGET "X" '((8 . "RET20X20PR"))))
  (setq prov 0)
  (setq e (ssname gpoRpR prov))
  (while e
    (if (= (cdr (assoc 0 (entget E))) "INSERT")
      (PROGN
        (SETQ PUNTOPROV (BUSATR E "PUNTO"))
        (SETQ DIFER (- (ATOF PUNTOPROV) (ATOF PUNTOPR)))
        (SETQ ELEVPROV (+ (ATOF ELEVATN) (* (* DIFER 20) PENDIENTE)))
        (setq bl (entnext E))
        (setq bl (entnext BL))
        (COMMAND "attedit" "" "" "" "" bl "V" "R" ELEVPROV "")
      )
    )
    (setq prov (1+ PROV))
    (setq e (ssname gpoRpR prov))
  )
  (SETQ GPORPR (SSADD))
  (SETQ GPORPR (SSGET "X" '((8 . "RET20X20PR"))))
  (setq e (ssname gpoRPR 0))
  (setq conta 1)
  (setq ArcDES (open "c:\\TOPOGRAF\\PROV2.CSV" "w"))
  (while e
    (SETQ LINEA "")
    (if (= (cdr (assoc 0 (entget E))) "INSERT")
      (PROGN
        (SETQ ELEVA (BUSATR E "ELEV"))
        (SETQ CODIG (BUSATR E "CODE"))
        (SETQ PUNTO (cdr (assoc 10 (entget E))))
        (SETQ X (CAR PUNTO))
        (SETQ X (RTOS X 2 8))
        (SETQ Y (CADR PUNTO))
        (SETQ Y (RTOS Y 2 8))
        (SETQ LINEA (STRCAT X "," Y "," ELEVA "," (ITOA CONTA)  "," CODIG))
      )
    )
    (IF (/= LINEA "")
       (WRITE-LINE LINEA ARCDES)
    )
    (setq e (ssname gpoRPR conta))
    (setq conta (1+ conta))
  )
  (CLOSE ARCDES)
  (COMMAND "SHELL" (strcat cdrive ":\\SURFER6\\GSMAC32.EXE /X " RUTA "NIVLOT2.BAS"))
  (setq archC (OPEN "C:\\TEMP.TMP" "w"))
  (WRITE-LINE "N" ARCHC)
  (CLOSE ARCHC)
  (setq lprov "N")
  (WHILE (/= LPROV "S")
    (setq archc nil)
    (WHILE (= ARCHC NIL)
      (COMMAND "DELAY" "5000")
      (setq archC (OPEN "C:\\TEMP.TMP" "r"))
    )
    (setq LPROV (READ-LINE ARCHC))
    (print lprov)
;    (print (strcat "corte" vcorte "  < terrap" vterrap))
    (CLOSE ARCHC)
  )
;  (setq archvol (open "editor1.txt" "r"))
;  (repeat 27
;    (read-line archvol)
;  )
;  (setq vcorte (read-line archvol))
;  (setq vterrap (read-line archvol))
;  (close archvol)
;  (SETQ LNG (STRLEN vcorte))
;  (setq vcorte (substr vcorte 25 (- lng 1)))
;  (SETQ LNG (STRLEN vterrap))
;  (setq vterrap (substr vterrap 26 (- lng 1)))
;  (SETQ ELEVG2 ELEVG1)
;  (SETQ ELEVG1 ELEVATN)
;  (SETQ ARCHSVOL (OPEN "C:\\VOL.TMP" "a"))
;  (WRITE-LINE (strcat VCORTE "," vterrap "," elevatn) ARCHSVOL)
;  (CLOSE ARCHSVOL)   
;  (IF (AND (> (/ (ATOF VCORTE) (ATOF VTERRAP)) 0.9) (< (/ (ATOF VCORTE) (ATOF VTERRAP)) 1.1) (= VRETORNO 0)) (PROGN (SETQ VSUMA 0.08) (SETQ VRETORNO 1)))
;  (IF (AND (> (/ (ATOF VCORTE) (ATOF VTERRAP)) 0.98) (< (/ (ATOF VCORTE) (ATOF VTERRAP)) 1.04) (= VRETORNO2 0)) (PROGN (SETQ VSUMA 0.01) (SETQ VRETORNO2 1)))
;  (if (> (atof vterrap) (atof vcorte))
;    (progn
;      (setq elevatn (rtos (- (atof elevatn) vsuma) 2 8))  
;      (setq resultado "terrap")
;    )
;    (progn
;      (setq elevatn (rtos (+ (atof elevatn) vsuma) 2 8))
;      (setq resultado "corte")
;    )
;  )
;  (if (OR (= ELEVATN ELEVG1) (= ELEVATN ELEVG2))
;      (PROGN
;        (if (> (atof vterrap) (atof vcorte))
;          (setq elevatn (rtos (+ (atof elevatn) vsuma) 2 8))  
;          (setq elevatn (rtos (- (atof elevatn) vsuma) 2 8))
;        )
;        (setq vsuma (- vsuma (* vsuma 0.3)))
;        (if (> (atof vterrap) (atof vcorte))
;          (setq elevatn (rtos (- (atof elevatn) vsuma) 2 8))  
;          (setq elevatn (rtos (+ (atof elevatn) vsuma) 2 8))
;       )
;      )
;  )
; )
;  (COMMAND "SHELL" (strcat cdrive ":\\SURFER6\\GSMAC32.EXE /X " RUTA "NIVLOT2.BAS"))
  (setq archC (OPEN "C:\\resultado.TMP" "r"))
  (setq LPROV (READ-LINE ARCHC))
  (setq LPROV2 (READ-LINE ARCHC))
  (close arch)
  (setq vcorte (rtos (atof lprov) 2 3))
  (setq vterrap (rtos (atof lprov) 2 3))

;  (alert (strcat "inicial" lprov))
;  (alert (strcat "final" lprov2))
  (SETQ ELEVATN (rtos (+ (atof ELEVATN) (ATOF LPROV2)) 2 8))
  (SETQ prov (rtos (+ (atof ELEVATN) (ATOF LPROV2)) 2 3))
  (COMMAND "attedit" "" "" "" "" bl "V" "R" prov "")
  (SETQ GPORPR (SSADD))
  (SETQ GPORPR (SSGET "X" '((8 . "RET20X20PR"))))
  (setq prov 0)
  (setq e (ssname gpoRpR prov))
  (while e
    (if (= (cdr (assoc 0 (entget E))) "INSERT")
      (PROGN
        (SETQ PUNTOPROV (BUSATR E "PUNTO"))
        (SETQ DIFER (- (ATOF PUNTOPROV) (ATOF PUNTOPR)))
        (SETQ ELEVPROV (rtos (+ (ATOF ELEVATN) (* (* DIFER 20) PENDIENTE)) 2 3))
        (setq bl (entnext E))
        (setq bl (entnext BL))
        (COMMAND "attedit" "" "" "" "" bl "V" "R" ELEVPROV "")
      )
    )
    (setq prov (1+ PROV))
    (setq e (ssname gpoRpR prov))
  )
  (SETQ GPORPR (SSADD))
  (SETQ GPORPR (SSGET "X" '((8 . "RET20X20PR"))))
  (setq e (ssname gpoRPR 0))
  (setq conta 1)
  (setq ArcDES (open "c:\\TOPOGRAF\\PROV2.CSV" "w"))
  (while e
    (SETQ LINEA "")
    (if (= (cdr (assoc 0 (entget E))) "INSERT")
      (PROGN
        (SETQ ELEVA (BUSATR E "ELEV"))
        (SETQ CODIG (BUSATR E "CODE"))
        (SETQ PUNTO (cdr (assoc 10 (entget E))))
        (SETQ X (CAR PUNTO))
        (SETQ X (RTOS X 2 8))
        (SETQ Y (CADR PUNTO))
        (SETQ Y (RTOS Y 2 8))
        (SETQ LINEA (STRCAT X "," Y "," ELEVA "," (ITOA CONTA)  "," CODIG))
      )
    )
    (IF (/= LINEA "")
       (WRITE-LINE LINEA ARCDES)
    )
    (setq e (ssname gpoRPR conta))
    (setq conta (1+ conta))
  )
  (CLOSE ARCDES)
;  (COMMAND "SHELL" (strcat cdrive ":\\SURFER6\\GSMAC32.EXE /X " RUTA "NIVLOT2P-5.BAS"))
;  (setq archC (OPEN "C:\\TEMP.TMP" "w"))
;  (WRITE-LINE "N" ARCHC)
;  (CLOSE ARCHC)
;  (setq lprov "N")
;  (WHILE (/= LPROV "S")
;    (setq archc nil)
;    (WHILE (= ARCHC NIL)
;      (COMMAND "DELAY" "5000")
;      (setq archC (OPEN "C:\\TEMP.TMP" "r"))
;    )
;    (setq LPROV (READ-LINE ARCHC))
;    (print lprov)
;    (CLOSE ARCHC)
;  )


  (COMMAND "SHELL" (strcat cdrive ":\\SURFER6\\GSMAC32.EXE /X " RUTA "NIVLOT3.BAS"))
  (setq archC (OPEN "C:\\TEMP.TMP" "w"))
  (WRITE-LINE "N" ARCHC)
  (CLOSE ARCHC)
  (setq lprov "N")
  (WHILE (/= LPROV "S")
    (setq archc nil)
    (WHILE (= ARCHC NIL)
      (COMMAND "DELAY" "5000")
      (setq archC (OPEN "C:\\TEMP.TMP" "r"))
    )
    (setq LPROV (READ-LINE ARCHC))
    (print lprov)
    (CLOSE ARCHC)
   )
  (setq archvol (open "editor1.txt" "r"))
  (repeat 27
    (read-line archvol)
  )
  (SETQ GPOP (SSADD))                                                                               ;seleciona nomnum
  (SETQ GPOP (SSGET "X" '((2 . "NOMNUM"))))
  (IF (/= (SSLENGTH GPOP) 1)
   (PROGN
     (ALERT "hay dos blocks con attributos de nombre y numero de lote")
     (setq ex (car (entsel "Selecciona el block fuente" )))
   )
   (SETQ EX (SSNAME GPOP 0))
  )
  (setq no-lt (busatr ex "NO-LOTE"))
  (setq nombrex (busatr ex "NOMBRE"))
  (setq vcorte (read-line archvol))
  (setq vterrap (read-line archvol))
  (close archvol)
  (SETQ LNG (STRLEN vcorte))
  (setq vcorte (substr vcorte 25 (- lng 1)))
  (SETQ LNG (STRLEN vterrap))
  (setq vterrap (substr vterrap 26 (- lng 1)))
  (SETQ VCORTE (RTOS (/ (+ (ATOF VCORTE) (ATOF VTERRAP)) 2) 2 3))
  (command "insert" (strcat ruta "BLOCKS\\AREAS Y VOLUMENES") pTo "" "" "0" "" "" "" "" "" "" "" "" "" "")           ;INSERTA AREAS Y VOLUMENES
  (COMMAND "AREA" "E" POLENVOLVENTE)
  (SETQ AP (RTOS (GETVAR "AREA") 2 3))
  (setq bl (entnext (ENTLAST)))
  (COMMAND "attedit" "" "" "" "" bl "V" "R" AP "")
  (setq bl (entnext BL))
  (COMMAND "attedit" "" "" "" "" bl "V" "R" VCORTE "")
  (setq bl (entnext BL))
  (COMMAND "attedit" "" "" "" "" bl "V" "R" Vcorte "")
  (SETQ OPPRV (BSLAYER "CURVASPR"))
  (IF (/= OPPRV "S") (COMMAND "LAYER" "M" "CURVASPR" "C" "RED" "" ""))
  (COMMAND "DXFIN" "C:\\NIVLOT2.DXF")
  (SETQ GPOCURVAS (SSGET "X" '((8 . "GSLAYER"))))
  (COMMAND "CHANGE" GPOCURVAS "" "P" "LA" "CURVASPR" "")
  (SETQ VLIMPIA 1)
  (SETQ e polenvolvente)
  (SETQ LAYCONG "CURVASPR")
  (if (= (getvar "acadver") "14.0")
    (progn
      (LOAD (STRCAT RUTA "LIMPIA14"))
      (C:LIMPI)
    )
    (progn
      (command "expresstools")
      (LOAD (STRCAT RUTA "LIMPIA"))
      (SETQ na E)
      (SETQ P1 PE)
      (C:LIMPI)
    )
  )
  (SETQ VLIMPIA 0)
  (COMMAND "REGENALL")
  (setq gpor20 (ssget "x" '((8 . "RET20X20PR"))))
  (command "change" gpor20 "" "p" "la" "nivprf" "")
;  (setq ex 1.13)
;  (setq ey 1.13) 
;  (COMMAND "INSERT" (STRCAT RUTA "BLOCKS\\PUN2") (list ex ey) ".1" "" "" "" "" "" "" "" "" "")
;  (SETQ UL (ENTLAST))
;  (COMMAND "CHANGE" UL "" "P" "LA" "NIVPRF" "")
;  (SETQ OPINSAT 0)
;  (SETQ Nomblo "PUN2")
;  (SETQ tt 1.00)
;  (SETQ NOMARCH "C:\\PERF2.CSV")
;  (SETQ Ini 1)
;  (SETQ Fin 10000)
;  (SETQ tri "2")
;  (setq lisblo (tblsearch "block" nomblo))
;  (ABLOQUE)
;  (setq arch (OPEN nomarch "r"))
;  (if arch
;    (LEE)
;    (print "\n Archivo no encontrado ")
;  )
;  (close arch)
;  (setq arch (OPEN NOMARCH "r"))
;  (if arch
;    (LEE2)
;  )
;  (close arch)
;  (entdel ul)
;  (SETQ OPINSAT 1)
  (SETQ GPORTN (SSADD))
  (SETQ GPORTN (SSGET "X" '((8 . "NIVPRF"))))
  (SETQ GPORET (SSADD))
  (SETQ GPORET (SSGET "X" '((8 . "RET20X20"))))
  (COMMAND "ERASE" GPORTN "R")
  (SETQ PROV 0)
  (SETQ E (SSNAME GPORET prov))
  (SETQ X2 0.0)
  (SETQ Y2 0.0)
  (WHILE E
    (if (= (cdr (assoc 0 (entget E))) "POINT")
      (PROGN
        (SETQ PUNTO (cdr (assoc 10 (entget E))))
        (SETQ X (+ 0.0001 (CAR PUNTO)))
        (SETQ X (RTOS X 2 8))
        (SETQ Y (+ 0.0001 (CADR PUNTO)))
        (SETQ Y (RTOS Y 2 8))
        (SETQ X2 (- (CAR PUNTO) 0.0000001))
        (SETQ X2 (RTOS X2 2 8))
        (SETQ Y2 (- (CADR PUNTO) 0.0000001))
        (SETQ Y2 (RTOS Y2 2 8))
        (SETQ LINEA (STRCAT X "," Y ",0"))
        (SETQ LINEA2 (STRCAT X2 "," Y2 ",0"))
        (COMMAND "C" LINEA LINEA2)
      )
    )
    (setq PROV (1+ PROV))
    (setq e (ssname gpoRET PROV))
  )
  (COMMAND "" "")
  (SETQ GPORET (SSADD))
  (SETQ GPORET (SSGET "X" '((8 . "RET20X20"))))
  (SETQ PROV 0)
  (SETQ E (SSNAME GPORET prov))
  (SETQ X2 0.0)
  (SETQ Y2 0.0)
  (WHILE E
    (if (= (cdr (assoc 0 (entget E))) "POINT")
      (PROGN
        (SETQ PUNTO (cdr (assoc 10 (entget E))))
        (SETQ X (+ 0.0001 (CAR PUNTO)))
        (SETQ X (RTOS X 2 8))
        (SETQ Y (+ 0.0001 (CADR PUNTO)))
        (SETQ Y (RTOS Y 2 8))
        (SETQ X2 (- (CAR PUNTO) 0.0000001))
        (SETQ X2 (RTOS X2 2 8))
        (SETQ Y2 (- (CADR PUNTO) 0.0000001))
        (SETQ Y2 (RTOS Y2 2 8))
        (setq gpoprov (ssadd))
        (SETQ GPOPROV (SSGET "C" (suma punto 0.001 0.001) (suma punto -0.001 -0.001)))
        (SETQ E2 (SSNAME GPOPROV 0))
        (SETQ CPROV 1)
        (WHILE E2
          (SETQ LAYERB (cdr (assoc 8 (entget E2))))
          (SETQ NOMBREB (cdr (assoc 2 (entget E2))))
          (SETQ TIPOBJ (cdr (assoc 0 (entget E2))))
          (SETQ XYB (cdr (assoc 10 (entget E2))))
          (IF (= TIPOBJ "INSERT")
            (IF (= (STRCASE NOMBREB) "PUN2")
              (PROGN
                (IF (= (STRCASE LAYERB) "NIVPRF")
                  (IF (> 0.005 (DISTANCE XYB PUNTO))
                    (SETQ EPROY (BUSATR E2 "ELEV"))
                  )
                )
                (IF (= (STRCASE LAYERB) "NIVTNF")
                  (IF (> 0.005 (DISTANCE XYB PUNTO))
                    (SETQ ETN (BUSATR E2 "ELEV"))
                  )
                )
              )
            )
          )
          (SETQ E2 (SSNAME GPOPROV CPROV))
          (SETQ CPROV (1+ CPROV))
        )
         (IF (> (ATOF EPROY) (ATOF ETN))
           (PROGN
             (command "insert" (strcat ruta "BLOCKS\\terraplenn.dwg") PUNTO "" "" "" "" "" "" "" "" "" "" "")
             (SETQ BL (ENTLAST))
             (setq bl (entnext BL))
             (COMMAND "attedit" "" "" "" "" bl "V" "R" (rtos (- (ATOF EPROY) (ATOF ETN)) 2 3) "")
             (setq bl (entnext BL))
             (COMMAND "attedit" "" "" "" "" bl "V" "R" EPROY "")
             (setq bl (entnext BL))
             (COMMAND "attedit" "" "" "" "" bl "V" "R" ETN "")
           )
           (PROGN
             (command "insert" (strcat ruta "BLOCKS\\corten.dwg") PUNTO "" "" "" "" "" "" "" "" "" "" "")
             (SETQ BL (ENTLAST))
             (setq bl (entnext BL))
             (COMMAND "attedit" "" "" "" "" bl "V" "R" (rtos (- (ATOF ETN) (ATOF EPROY)) 2 3) "")
             (setq bl (entnext BL))
             (COMMAND "attedit" "" "" "" "" bl "V" "R" EPROY "")
             (setq bl (entnext BL))
             (COMMAND "attedit" "" "" "" "" bl "V" "R" ETN "")
           )
         )
      )
    )
    (setq PROV (1+ PROV))
    (setq e (ssname gpoRET PROV))
  )
)

(defun pendiente1 ()
    (setq vcorte "1")
    (setq vterrap "2")
    (setq vsuma 0.2)
    (setq opcorte 0)
    (SETQ ARCHSVOL (OPEN "C:\\VOL.TMP" "w"))
    (CLOSE ARCHSVOL)   
    (SETQ VRETORNO 0)
    (SETQ VRETORNO2 0)
    (SETQ ELEVG1 NIL)
    (SETQ ELEVG2 "N")
;  (while (and (/= (RTOS (ATOF vcorte) 2 4) (RTOS (ATOF vterrap) 2 4)) (/= elevg2 elevg1 elevaCIOn))
    (setq archC (OPEN "C:\\VSUMA.TMP" "w"))
    (SETQ LPROV (RTOS (atof ELEVACION) 2 15))
    (WRITE-LINE LPROV ARCHC)
    (CLOSE ARCHC)
  (COMMAND "SHELL" (strcat cdrive ":\\SURFER6\\GSMAC32.EXE /X " RUTA "NIVLOT2-2.BAS"))        ' REALIZA GRID
  (setq archC (OPEN "C:\\TEMP.TMP" "w"))
  (WRITE-LINE "N" ARCHC)
  (CLOSE ARCHC)
  (setq lprov "N")
  (WHILE (/= LPROV "S")
    (setq archc nil)
    (WHILE (= ARCHC NIL)
      (COMMAND "DELAY" "5000")
      (setq archC (OPEN "C:\\TEMP.TMP" "r"))
    )
    (setq LPROV (READ-LINE ARCHC))
    (print lprov)
;    (print (strcat "corte" vcorte "  < terrap" vterrap))
    (CLOSE ARCHC)
  )
    (COMMAND "SHELL" (strcat RUTA "VOL2.EXE"))                                     ;LLAMA VOLUMENES 2
    (setq archC (OPEN "C:\\TEMP.TMP" "w"))
    (WRITE-LINE "N" ARCHC)
    (CLOSE ARCHC)
    (setq lprov "N")
   (WHILE (/= LPROV "S")
    (setq archc nil)
    (WHILE (= ARCHC NIL)
     (COMMAND "DELAY" "5000")
     (setq archC (OPEN "C:\\TEMP.TMP" "r"))
    )
    (setq LPROV (READ-LINE ARCHC))
    (print lprov)
    (CLOSE ARCHC)
   )
    (setq archvol (open "editor1.txt" "r"))
    (repeat 21
      (read-line archvol)
    )
    (setq vcorte (read-line archvol))
    (setq vterrap (read-line archvol))
    (close archvol)
    (SETQ LNG (STRLEN vcorte))
    (setq vcorte (substr vcorte 25 (- lng 1)))
    (SETQ LNG (STRLEN vterrap))
    (setq vterrap (substr vterrap 26 (- lng 1)))
;    (SETQ ELEVG2 ELEVG1)
;    (SETQ ELEVG1 ELEVAcion)
;    (if (> (atof vterrap) (atof vcorte))
;      (progn
;       (setq elevacion (rtos (- (atof elevacion) vsuma) 2 8))   
;       (setq resultado "terrap")
;      )
;      (progn
;       (IF (/= VCORTE VTERRAP)
;        (setq elevacion (rtos (+ (atof elevacion) vsuma) 2 8))
;       )
;       (setq resultado "corte")
;      )
;    )
;    (if (AND (/= ELEVAcion ELEVG1) (= ELEVACION ELEVG2))
;         (setq vsuma (- vsuma (* vsuma 0.3)))
;    )
;   );
  (setq archC (OPEN "C:\\resultado.TMP" "r"))
  (setq LPROV (READ-LINE ARCHC))
  (setq ELEVACION (READ-LINE ARCHC))
  (close arch)
  (SETQ GPOP (SSADD))
  (SETQ GPOP (SSGET "X" '((2 . "NOMNUM"))))                                       ;selecciona nomnum
  (IF (/= (SSLENGTH GPOP) 1)
   (PROGN
     (ALERT "hay dos blocks con attributos de nombre y numero de lote")
     (setq ex (car (entsel "Selecciona el block fuente" )))
   )
   (SETQ EX (SSNAME GPOP 0))
  )
  (setq no-lt (busatr ex "NO-LOTE"))
  (setq nombrex (busatr ex "NOMBRE"))
  (SETQ VCORTE (RTOS (/ (+ (ATOF VCORTE) (ATOF VTERRAP)) 2) 2 3))
  (command "insert" (strcat ruta "BLOCKS\\AREAS Y V 2.dwg") pE "" "" "0" "" "" "" "" "" "")
   (COMMAND "AREA" "E" POLENVOLVENTE)
   (SETQ AP (RTOS (GETVAR "AREA") 2 3))
  (setq bl (entnext (ENTLAST)))
  (COMMAND "attedit" "" "" "" "" bl "V" "R" AP "")
  (setq bl (entnext BL))
  (COMMAND "attedit" "" "" "" "" bl "V" "R" VCORTE "")
  (setq bl (entnext BL))
  (COMMAND "attedit" "" "" "" "" bl "V" "R" Vcorte "")
   (SETQ GPORET (SSADD))
   (SETQ GPORET (SSGET "X" '((8 . "RET20X20"))))
   (SETQ PROV 0)
   (SETQ E (SSNAME GPORET prov))
   (SETQ X2 0.0)
   (SETQ Y2 0.0)
   (SETQ EPROY ELEVACION)
   (SETQ FILEDESC (OPEN "C:\\TOPOGRAF\\NIVELES20.CSV" "a"))
   (WHILE E
     (if (= (cdr (assoc 0 (entget E))) "POINT")
       (PROGN
         (SETQ PUNTO (cdr (assoc 10 (entget E))))
         (SETQ X (+ 0.0001 (CAR PUNTO)))
         (SETQ X (RTOS X 2 8))
         (SETQ Y (+ 0.0001 (CADR PUNTO)))
         (SETQ Y (RTOS Y 2 8))
         (SETQ X2 (- (CAR PUNTO) 0.0000001))
         (SETQ X2 (RTOS X2 2 8))
         (SETQ Y2 (- (CADR PUNTO) 0.0000001))
         (SETQ Y2 (RTOS Y2 2 8))
         (setq gpoprov (ssadd))
         (SETQ GPOPROV (SSGET "C" (suma punto 0.001 0.001) (suma punto -0.001 -0.001)))
         (SETQ E2 (SSNAME GPOPROV 0))
         (SETQ CPROV 1)
         (WHILE E2
           (SETQ LAYERB (cdr (assoc 8 (entget E2))))
           (SETQ NOMBREB (cdr (assoc 2 (entget E2))))
           (SETQ TIPOBJ (cdr (assoc 0 (entget E2))))
           (SETQ XYB (cdr (assoc 10 (entget E2))))
           (IF (= TIPOBJ "INSERT")
             (IF (= (STRCASE NOMBREB) "PUN2")
               (PROGN
                 (IF (= (STRCASE LAYERB) "NIVTNF")
                   (IF (> 0.005 (DISTANCE XYB PUNTO))
                     (SETQ ETN (BUSATR E2 "ELEV"))
                   )
                 )
               )
             )
           )
           (SETQ E2 (SSNAME GPOPROV CPROV))
           (SETQ CPROV (1+ CPROV))
         )
         (SETQ X (CAR PUNTO))
         (SETQ X (RTOS X 2 8))
         (SETQ Y (CADR PUNTO))
         (SETQ Y (RTOS Y 2 8))
         (IF (> (ATOF EPROY) (ATOF ETN))
           (PROGN
             (command "insert" (strcat ruta "BLOCKS\\terraplenn.dwg") PUNTO "1.6" "" "" "" "" "" "" "" "" "" "")
             (SETQ BL (ENTLAST))
             (setq bl (entnext BL))
             (COMMAND "attedit" "" "" "" "" bl "V" "R" (rtos (- (ATOF EPROY) (ATOF ETN)) 2 3) "")
             (setq bl (entnext BL))
             (COMMAND "attedit" "" "" "" "" bl "V" "R" (RTOS (ATOF EPROY) 2 3) "")
             (setq bl (entnext BL))
             (COMMAND "attedit" "" "" "" "" bl "V" "R" (RTOS (ATOF ETN) 2 3) "")
             (setq liprov (strcat x "," y "," etn "," eproy "," (rtos (- (ATOF EPROY) (ATOF ETN)) 2 3) ", TERRAP"))
             (write-line liprov filedesc)
           )
           (PROGN
             (command "insert" (strcat ruta "BLOCKS\\corten.dwg") PUNTO "1.6" "" "" "" "" "" "" "" "" "" "")
             (SETQ BL (ENTLAST))
             (setq bl (entnext BL))
             (COMMAND "attedit" "" "" "" "" bl "V" "R" (rtos (- (ATOF ETN) (ATOF EPROY)) 2 3) "")
             (setq bl (entnext BL))
             (COMMAND "attedit" "" "" "" "" bl "V" "R" (RTOS (ATOF EPROY) 2 3) "")
             (setq bl (entnext BL))
             (COMMAND "attedit" "" "" "" "" bl "V" "R" (RTOS (ATOF ETN) 2 3) "")
             (setq liprov (strcat x "," y "," etn "," eproy "," (rtos (- (ATOF ETN) (ATOF EPROY)) 2 3) ", CORTE"))
             (write-line liprov filedesc)
           )
         )
       )
     )
     (setq PROV (1+ PROV))
     (setq e (ssname gpoRET PROV))
    )
 (close filedesc)
  (SETQ OPPRV (BSLAYER "OCULTO"))
  (IF (/= OPPRV "S") (COMMAND "LAYER" "M" "OCULTO" "C" "GREEN"  "" ""))
 (SETQ GPOG (SSGET "X" '((0 . "INSERT") (2 . "PUN2"))))
 (COMMAND "CHANGE" GPOG "" "P" "LA" "OCULTO" "")
  (COMMAND "LAYER" "S" "0" "F" "OCULTO" "" "")
  (command "move" "all" "" pto regreso)
   (command "zoom" "e")
 (alert "he Finalizado")
)
