(defun c:rbl ()
        (setq e (car (entsel "Selecciona el bloque a ROTAR : ")))
        (while (/= "INSERT" (cdr (assoc 0 (entget E))))
          (if (/= "INSERT" (cdr (assoc 0 (entget E))))
            (progn   
              (ALERT "\nEl objeto debe ser un block ")
              (setq E (car (entsel "\n Selecciona el bloque: ")))
            )
          )
        )
        (setq NOMBRE (cdr (assoc 2 (entget e))))
        (setq AN (getreal "Dame el angulo al que deseas rotar: "))
        (setq E (entnext))
        (while E
          (if (= "INSERT" (cdr (assoc 0 (entget E))))
              (if (= (strcase NOMBRE) (cdr (assoc 2 (entget E))))
                   (command "CHANGE" E "" "" "" AN)
              )
          )
         (setq E (entnext E))
        )
)
