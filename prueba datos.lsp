(defun c:prueba () 
  (C:LIBRERIA "grafica parametro clima estacion")
  (C:LIBRERIA "encuentra coincidencias")
  (C:LIBRERIA "UTM-GEO")
  (C:LIBRERIA "GEO-UTM")
  (C:LIBRERIA "encuentra zona horaria municipio")
  (C:LIBRERIA "CENTROIDE DE UN POLIGONO IRREGULAR2")
  (C:LIBRERIA "VERTICES TO BD POLYLINE")
  (C:LIBRERIA "BUSCA ESTACIONES CLIMATOLOGICAS CLICOM")
  (C:LIBRERIA "BUSCA ESTACIONES CLIMATOLOGICAS ERICK")
  (C:LIBRERIA "BUSCA ESTADO DE GEO")
  (C:LIBRERIA "tranforma coordenadas dibujo im")
  (C:LIBRERIA "escribe texto img")
  (C:LIBRERIA "acota grafica")
  (C:LIBRERIA "ENTRADAS Y SALIDAS AL REGISTRO DE OBJETOS DCL")
  (C:LIBRERIA "BUSCA ACCION OBJETOS DIALOGO")
  (C:LIBRERIA "descompacta cadena")
  (C:LIBRERIA "grafica parametro clima estacion")
  (C:LIBRERIA "controla grafica")
  (C:LIBRERIA "sector cuadricula")
  (C:LIBRERIA "muestra color")
  (C:LIBRERIA "numero de dias del mes fecha")
  (C:LIBRERIA "indice graficos fechas")
  (C:LIBRERIA "maximos")
  (C:LIBRERIA "correlacionr")
  (setq datoe1 (leebd "16006"))
  (setq datoe2 (leebd "16007"))
  (setq datoe3 (leebd "16012"))
  (setq datoe4 (leebd "16014"))
  (setq datoe5 (leebd "16015"))
  (setq datoe6 (leebd "16047"))
  (setq datoe7 (leebd "16056"))
  (setq datoe8 (leebd "16074"))
  (setq datoe9 (leebd "16082"))
  (setq datoe10 (leebd "16087"))
  (setq datoe11 (leebd "16088"))
  (setq datoe12 (leebd "16118"))
  (setq datoe13 (leebd "16123"))
  (setq datoe14 (leebd "16127"))
  (setq datoe15 (leebd "16133"))
  (setq datoe16 (leebd "16142"))
  (setq datoe17 (leebd "16146"))
  (setq datoe18 (leebd "16147"))
  (setq datoe19 (leebd "16164"))
  (setq datoe20 (leebd "16165"))
  (setq datoe21 (leebd "16171"))
  (setq datoe22 (leebd "16188"))
  (setq archivo (open "D:\\f\\prov.txt" "w"))
  (setq cont 22)
  (repeat 21
    (if (= cont 22) (setq varprv datoe1))
    (if (= cont 21) (setq varprv datoe2))
    (if (= cont 20) (setq varprv datoe3))
    (if (= cont 19) (setq varprv datoe4))
    (if (= cont 18) (setq varprv datoe5))
    (if (= cont 17) (setq varprv datoe6))
    (if (= cont 16) (setq varprv datoe7))
    (if (= cont 15) (setq varprv datoe8))
    (if (= cont 14) (setq varprv datoe9))
    (if (= cont 13) (setq varprv datoe10))
    (if (= cont 12) (setq varprv datoe11))
    (if (= cont 11) (setq varprv datoe12))
    (if (= cont 10) (setq varprv datoe13))
    (if (= cont 9) (setq varprv datoe14))
    (if (= cont 8) (setq varprv datoe15))
    (if (= cont 7) (setq varprv datoe16))
    (if (= cont 6) (setq varprv datoe17))
    (if (= cont 5) (setq varprv datoe18))
    (if (= cont 4) (setq varprv datoe19))
    (if (= cont 3) (setq varprv datoe20))
    (if (= cont 2) (setq varprv datoe21))
    (setq cont3 1)
    (repeat (1- cont)
      (if (= cont3 2) (setq varprv2 datoe2))
      (if (= cont3 3) (setq varprv2 datoe3))
      (if (= cont3 4) (setq varprv2 datoe4))
      (if (= cont3 5) (setq varprv2 datoe5))
      (if (= cont3 6) (setq varprv2 datoe6))
      (if (= cont3 7) (setq varprv2 datoe7))
      (if (= cont3 8) (setq varprv2 datoe8))
      (if (= cont3 9) (setq varprv2 datoe9))
      (if (= cont3 10) (setq varprv2 datoe10))
      (if (= cont3 11) (setq varprv2 datoe11))
      (if (= cont3 12) (setq varprv2 datoe12))
      (if (= cont3 13) (setq varprv2 datoe13))
      (if (= cont3 14) (setq varprv2 datoe14))
      (if (= cont3 15) (setq varprv2 datoe15))
      (if (= cont3 16) (setq varprv2 datoe16))
      (if (= cont3 17) (setq varprv2 datoe17))
      (if (= cont3 18) (setq varprv2 datoe18))
      (if (= cont3 19) (setq varprv2 datoe19))
      (if (= cont3 20) (setq varprv2 datoe20))
      (if (= cont3 21) (setq varprv2 datoe21))
      (if (= cont3 22) (setq varprv2 datoe22))
      (setq varprv (coincidencias varprv varprv2 4 6))
      (setq ndat (/ (/ (strlen varprv) 10) 2))
      (setq varprvx (substr varprv 1 (/ (strlen varprv) 2)))
      (setq varprvx2 (substr varprv (1+ (/ (strlen varprv) 2))))
      (if (/= varprvx "")
        (setq correlacion (correlacionr varprvx varprvx2 4 6))
        (setq correlacion 0.00)
      )
      (setq cont2 1)
      (repeat ndat
         (setq datox (substr varprvx (1+ (* (1- cont2) 10)) 10))
         (setq datox2 (substr varprvx2 (1+ (* (1- cont2) 10)) 10))
         (if (and (/= (substr datox 5 6) "xxxxxx") (/= (substr datox2 5 6) "xxxxxx"))
           (if (= cont2 1)
             (write-line (strcat datox "," datox2 "," (rtos correlacion 2 10) " " (itoa cont) " " (itoa cont3)) archivo)
             (write-line (strcat datox "," datox2) archivo)
           )
         )
         (setq cont2 (1+ cont2))
      )
      (write-line "" archivo)
      (setq cont3 (1+ cont3))
    )
    (setq cont (1- cont))
  )
  (close archivo)
)

(defun leebd (estacion)
  (setq variable 3)
  (setq procedencia "C")
         (setq diradicional "CLICOM")
         (setq extencion ".cli")
      (setq dirprim "\\hp\\")
 (setq ndec 2)
 (setq anchochr 6)
      (setq ldat1 "")
      (if (and (= procedencia "C") (/= optimizadiarioc nil)) (setq ldat1 (optimizabdiarios)))
      (if (= ldat1 "")
        (progn      
          (dos_getcancel "LEYENDO BD" "LEYENDO DATOS POR FAVOR ESPERE...")
          (IF (not (dos_getcanceL)) (exit))
          (dos_encrypt (strcat ruta "BASES DE DATOS\\DATOS CLIMATOLOGICOS\\" diradicional dirprim estacion extencion) (strcat "4avEjsD8GlñOpwrpfvc3071fdA" estacion "Ga4TykP8G5Umo9Ye513"))
          (setq archIVOindice (open (strcat ruta "BASES DE DATOS\\DATOS CLIMATOLOGICOS\\" diradicional dirprim estacion extencion) "r"))
          (setq ldat1x (read-line archIVOindice))
          (close archivoindice)
          (dos_encrypt (strcat ruta "BASES DE DATOS\\DATOS CLIMATOLOGICOS\\" diradicional dirprim estacion extencion) (strcat "4avEjsD8GlñOpwrpfvc3071fdA" estacion "Ga4TykP8G5Umo9Ye513"))
          (IF (not (dos_getcanceL)) (exit))
          (setq ldat1 (descompacta ldat1x))
          (IF (not (dos_getcanceL)) (exit))          
          (if (= procedencia "E")
            (progn
              (if (= controlbdace nil) (setq controlbdace 1))
              (setq cadenaprov (strcat estacion (itoa variable)))
              (setq valorx (list (cons 1 cadenaprov) (cons 2 ldat1)))
              (setq CONCATENADO (cons controlbdace valorx)) 
              (setq optimizadiarioe (append optimizadiarioe (list CONCATENADO)))
              (setq controlbdace (1+ controlbdace))
            )
          )
          (if (= procedencia "C")
            (progn
              (if (= controlbdacc nil) (setq controlbdacc 1))
              (setq cadenaprov (strcat estacion (itoa variable)))
              (setq valorx (list (cons 1 cadenaprov) (cons 2 ldat1)))
              (setq CONCATENADO (cons controlbdacC valorx)) 
              (setq optimizadiarioC (append optimizadiarioC (list CONCATENADO)))
              (setq controlbdacc (1+ controlbdacc))
            )
          )
          (dos_getcanceL t)
        )
      );if 
(setq ldat1 (maximos ldat1 "ME" 3 "190001"))
  (setq ldat1 ldat1)

)
