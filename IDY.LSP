(defun C:DY1 ()
    (setq PUNTO (getpoint " ELEVACION A TOMAR : "))
    (setq texto (car (entsel "Selecciona el texto: ")))
    (SETQ Y (CADR PUNTO))
    (SETQ Y (RTOS Y 2 3))
    (SETQ LNG (STRLEN y))
    (setq lng (1+ lng))
    (if (= (substr y (- lng 4) 4) ".000") (setq y (substr y 1 (- lng 5))))
    (COMMAND "CHANGE" texto "" "" "" "" "" "" (strcat "N=" Y))
)

(defun C:DY2 ()
    (setq PUNTO (getpoint " ELEVACION A TOMAR : "))
    (setq texto (car (entsel "Selecciona el texto: ")))
    (SETQ Y (CADR PUNTO))
    (SETQ Y (RTOS Y 2 3))
    (SETQ LNG (STRLEN y))
    (setq lng (1+ lng))
    (if (= (substr y (- lng 4) 4) ".000") (setq y (substr y 1 (- lng 5))))
    (COMMAND "CHANGE" texto "" "" "" "" "" "" (strcat "TN" Y))
)

(defun C:DX1 ()
    (setq PUNTO (getpoint " ELEVACION A TOMAR : "))
    (setq texto (car (entsel "Selecciona el texto: ")))
    (SETQ X (CAR PUNTO))
    (SETQ X (RTOS X 2 3))
    (SETQ LNG (STRLEN x))
    (setq lng (1+ lng))
    (if (= (substr x (- lng 4) 4) ".000") (setq x (substr x 1 (- lng 5))))
    (COMMAND "CHANGE" texto "" "" "" "" "" "" (STRCAT "E=" X))
)

(defun C:DY1B ()
    (setq PUNTO (getpoint " ELEVACION A TOMAR : "))
    (setq PUNTO2 (getpoint " PUNTO DESTINO : "))
    (SETQ Y (CADR PUNTO))
    (SETQ Y (RTOS Y 2 3))
    (COMMAND "INSERT" (STRCAT RUTA "BLOCKS\\PUN2") PUNTO2 "" "" "")
    (SETQ BLOCK (ENTLAST))
    (SETQ BLOCK (ENTNEXT BLOCK))
    (COMMAND "ATTEDIT" "" "" "" "" BLOCK "V" "R" "SECCION" "")
    (SETQ BLOCK (ENTNEXT BLOCK))
    (COMMAND "ATTEDIT" "" "" "" "" BLOCK "V" "R" Y "")
    (SETQ BLOCK (ENTNEXT BLOCK))
    (COMMAND "ATTEDIT" "" "" "" "" BLOCK "V" "R" "1" "")
)

(defun C:DX1B ()
    (setq PUNTO (getpoint " ELEVACION A TOMAR : "))
    (setq BLOCK (car (entsel "Selecciona el BLOCK: ")))
    (SETQ X (CAR PUNTO))
    (SETQ X (RTOS X 2 0))
    (SETQ BLOCK (ENTNEXT BLOCK))
    (SETQ BLOCK (ENTNEXT BLOCK))
    (COMMAND "ATTEDIT" "" "" "" "" BLOCK "V" "R" Y "")
)
