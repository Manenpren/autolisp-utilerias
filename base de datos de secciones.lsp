(defun c:bdsec ()
  (C:LIBRERIA "BUSCA VALOR DE ATRIBUTO")
  (COMMAND "UNDO" "M")
  (COMMAND "VIEW" "S" "C")
  (PRINT "SELECCIONA LOS BLOCKS PARA HACER LA BASE DE DATOS")
  (SETQ GPOG (SSGET))
  (setq arcdes (getfiled "ARCHIVO DE Descarga" "*." "CSV" 19))
  (SETQ f1 (OPEN arcdes "w"))
  (WRITE-LINE "CADENAMIENTO,CORTE,FILTRO, BASE, CARPETA, BANQUETAS" F1)
  (SETQ P2 0)  
  (SETQ PROV (SSNAME GPOG P2))
  (setq NOMBLO (cdr (assoc 2 (entget PROV))))
  (WHILE (/= PROV NIL)
    (COMMAND "INSERT" NOMBLO "0,0" "" "" "")
    (SETQ X (ENTLAST))
    (COMMAND "EXPLODE" X "")
    (SETQ GPOA (SSGET "P"))
    (SETQ P 0)
    (SETQ PROV2 (SSNAME GPOA P))
    (WHILE (/= (cdr (assoc 0 (entget PROV2))) "INSERT")
      (SETQ P (1+ P))
      (SETQ PROV2 (SSNAME GPOA P))
    )
;    (SETQ CORTE (BUSATR PROV2 "AC"))
;    (SETQ FILTRO (BUSATR PROV2 "AT"))
;    (SETQ BASE (BUSATR PROV2 "AS"))
;    (SETQ CARPETA (BUSATR PROV2 "AB"))
;    (SETQ BANQUETAS (BUSATR PROV2 "AC'"))
;    (COMMAND "ERASE" GPOA "")
;    (WRITE-LINE (STRCAT NOMBLO "," CORTE "," FILTRO "," BASE "," CARPETA "," BANQUETAS) F1)
    (setq xyzh (cdr (assoc 10 (entget PROV2))))
    (command "zoom" "c" xyzh "20")
   (setq texto (car (entsel "Selecciona el texto: ")))
   (setq cadena (cdr (assoc 1 (entget texto))))
   (setq lng (strlen cadena))
   (setq lngn (substr cadena 1 (1- lng)))
   (setq lngn (atof lngn))
   (setq lngn (* lngn 100))
   (COMMAND "CHANGE" texto "" "" "" "" "" "" (strcat (rtos lngn 2 1) " %"))
;    (COMMAND "SCALE" PROV2 "" XYZH "0.4")
;    (command "move" prov2 "" xyzh pause)
    (command "block" nomblo "y" "0,0" gpoa "")
    (command "erase" gpoa "")
    (SETQ P2 (1+ P2))   
    (SETQ PROV (SSNAME GPOG P2))
    (IF (/= PROV NIL)
      (setq NOMBLO (cdr (assoc 2 (entget PROV))))
    )
  )
  (CLOSE F1)
)
