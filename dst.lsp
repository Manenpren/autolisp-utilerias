(defun C:dst ()
  (setq dst1 (getdist "distancia a calcular"))
  (setq ob (car (entsel "selecciona block del centro")))
  (setq elev1 (busatr ob "ELEV"))  
  (setq lf (* dst1 0.02))
  (setq lf (rtos (- (atof elev1) lf) 2 3))
  (setq punto (getpoint "punto de insercion del block")) 
  (command "insert" "pun2" punto "" "" "" "INT" lf "1" "" "" "")
)

(DEFUN BUSATR (E ATR)
 (SETQ E (ENTNEXT E))
 (SETQ R 0)
 (WHILE (= "ATTRIB" (cdr (assoc 0 (entget E))))
   (if (= "ATTRIB" (cdr (assoc 0 (entget E))))
      (if (= ATR (cdr (assoc 2 (entget E))))
       (PROGN
        (setq vALAT (cdr (assoc 1 (entget E))))
       )
      )
   )
   (SETQ R (1+ R))
   (SETQ E (ENTNEXT E))
 )
 (PRINT ValAT)
)
