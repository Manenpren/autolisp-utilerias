(DEFUN BUSATR (E ATR)
 (SETQ E (ENTNEXT E))
 (SETQ R 0)
 (WHILE (= "ATTRIB" (cdr (assoc 0 (entget E))))
   (if (= "ATTRIB" (cdr (assoc 0 (entget E))))
      (if (= ATR (cdr (assoc 2 (entget E))))
       (PROGN
        (setq vALAT (cdr (assoc 1 (entget E))))
       )
      )
   )
   (SETQ R (1+ R))
   (SETQ E (ENTNEXT E))
 )
 (PRINT ValAT)
)

(DEFUN C:REG ()
  (SETQ E (CAR (ENTSEL "\n SELECCIONA EL BLOCK ELEVACION :")))
  (SETQ ELEVB (BUSATR E "ELEV"))
  (SETQ XYZ (cdr (assoc 10 (entget E))))
  (SETQ PRF (GETREAL " \n CUAL ES LA PROFUNDIDAD : "))
  (COMMAND "INSERT" "REGELEV" XYZ "" "" "")
    (SETQ ENTP(ENTLAST))
    (SETQ ENTP(ENTNEXT ENTP))
    (COMMAND "ATTEDIT" "" "" "" "" ENTP "V" "R" (RTOS (- (ATOF ELEVB) PRF)2 3) "")
    (SETQ ENTP(ENTNEXT ENTP))
    (COMMAND "ATTEDIT" "" "" "" "" ENTP "V" "R" ELEVB "")
    (SETQ ENTP(ENTNEXT ENTP))
    (COMMAND "ATTEDIT" "" "" "" "" ENTP "V" "R" (RTOS (- (ATOF ELEVB) (- (ATOF ELEVB) PRF))) "" "" "")
)
