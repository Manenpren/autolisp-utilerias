(defun C:creg ()
  (C:LIBRERIA "BUSCA VALOR DE ATRIBUTO")
  (setq blelev (car (entsel "Selecciona el block de elevacion : ")))
  (setq reg (car (entsel "Selecciona el block a modificar : ")))
  (setq elevacion (busatr blelev "ELEV"))
  (setq elevacion (atof elevacion))
  (setq eleva1 (+ elevacion 0.22))
  (SETQ ENTP (ENTNEXT reg))
  (COMMAND "ATTEDIT" "" "" "" "" ENTP "V" "R" (rtos (1- eleva1)2 3) "") 
  (SETQ ENTP (ENTNEXT entp))
  (COMMAND "ATTEDIT" "" "" "" "" ENTP "V" "R" (rtos eleva1 2 3) "") 
  (SETQ ENTP (ENTNEXT entp))
  (COMMAND "ATTEDIT" "" "" "" "" ENTP "V" "R" "1.000" "") 
)
