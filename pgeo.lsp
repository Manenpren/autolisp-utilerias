(defun c:pgeo1 ()
  (C:LIBRERIA "DECIMALTOSEXAGESIMAL3")
  (C:LIBRERIA "UTM-GEO")
  (SETQ xyz (GETPOINT "\n Punto a sacar su coordenada "))
  (setq xyz (list (car xyz) (cadr xyz)))
  (if (= zonah nil) (setq zonah "00"))
  (SETQ zonah1 (GETSTRING (strcat "\n ZONA UTM HORARIA <" zonah ">:")))
  (IF (/= zonah1 "")
    (SETQ zonah zonah1)
  )
  (setq puntogeo (UTM-GEO xyz (ATOI ZONAH)))
  (SETQ LAT (CAR puntoGEO))
  (SETQ LONG (CADR puntoGEO))
  (setq cadenax1 (DECSEXA lat))
  (setq cadenax2 (DECSEXA long))
  (print (strcat cadenax2 " " cadenax1))
)
