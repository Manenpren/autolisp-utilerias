(defun c:PP1 ()
  (C:LIBRERIA "BUSCA VALOR DE ATRIBUTO")
  (C:LIBRERIA "VERTICES DE UNA LWPOLYLINE")
  (C:LIBRERIA "BUSCA LAYER EN BASE DE DATOS")
  (setq cdrive (substr ruta 1 1))
  (setq os (getvar "osmode"))
  (COMMAND "UNDO" "M")
  (command "OSNAP" "none")
  (COMMAND "LUNITS" 2)
  (COMMAND "LUPREC" 7)
  (COMMAND "AUNITS" 0)
  (COMMAND "AUPREC" 4)
  (COMMAND "ANGDIR" 0)
  (COMMAND "ANGBASE" 0.0)
  (COMMAND "DIMZIN" 0)
  (COMMAND "DRAGMODE" "AUTO")
  (SETQ OPPRV (BSLAYER "cruces"))
  (IF (/= OPPRV "S") (COMMAND "LAYER" "M" "cruces" "C" "yelloW" "" ""))
  (SETQ OPPRV (BSLAYER "TEXTOS"))
  (IF (/= OPPRV "S") (COMMAND "LAYER" "M" "TEXTOS" "C" "RED" "" ""))
  (command "insert" (strcat ruta "BLOCKS\\PPCH.dwg") PAUSE "" "" "")
  (setq PTO (cdr (assoc 10 (entget (ENTLAST))))) 
  (COMMAND "EXPLODE" (ENTLAST) "")
;  (SETQ PTO (GETPOINT "\n Punto central del dibujo "))
  (COMMAND "LAYER" "s" "0" "")

  (SETQ GPOP (SSADD))                                                                               ;AREAS Y VOLUMENES
  (SETQ GPOP (SSGET "X" '((2 . "AREAS Y V 2"))))
  (IF (/= (SSLENGTH GPOP) 1)
   (PROGN
    (SETQ GPOP (SSGET "X" '((2 . "AREAS Y VOLUMENES"))))
    (SETQ EX (SSNAME GPOP 0))
   )
   (SETQ EX (SSNAME GPOP 0))
  )
  (setq AP (busatr ex "AREA"))
  (setq VCOR (busatr ex "VCORTE"))
  (setq VTERR (busatr ex "VTERAP"))
  (COMMAND "Erase" EX "")

  (SETQ GPOP (SSADD))                                                                               ;seleciona nomnum
  (SETQ GPOP (SSGET "X" '((2 . "NOMNUM"))))
  (IF (/= (SSLENGTH GPOP) 1)
   (PROGN
     (ALERT "hay dos blocks con attributos de nombre y numero de lote")
     (setq ex (car (entsel "Selecciona el block fuente" )))
   )
   (SETQ EX (SSNAME GPOP 0))
  )
  (setq PROPT (busatr ex "NOMBRE"))
  (setq name (getvar "dwgname"))
  (SETQ LNG (STRLEN NAME))
  (SETQ NO-LT (SUBSTR NAME 1 (- LNG 4)))
  (IF (= NO-LT NIL)
    (setq no-lt (busatr ex "NO_LOTE"))
  )

  (setq ap (rtos (atof ap) 2 3))
  (command "insert" (strcat ruta "BLOCKS\\AREASF.DWG") (SUMA PTO 184.130 -12.706) "" "" "0" "" "" "" "" "" "" "" "" "" "")           ;INSERTA AREAS Y VOLUMENES
  (setq blc (entlast))
  (setq blc (entnext blc))
  (COMMAND "attedit" "" "" "" "" blc "V" "R" VCOR "")
  (setq blc (entnext blc))
  (COMMAND "attedit" "" "" "" "" blc "V" "R" VTERR "")
  (setq blc (entnext blc))
  (COMMAND "attedit" "" "" "" "" blc "V" "R" PROPT "")
  (setq blc (entnext blc))
  (COMMAND "attedit" "" "" "" "" blc "V" "R" AP "")
  (setq blc (entnext blc))
  (COMMAND "attedit" "" "" "" "" blc "V" "R" NO-LT "")
  (SETQ LNG (STRLEN AP))
  (SETQ HAS (substr AP 1 (- lng 8)))
  (IF (= HAS "") (SETQ HAS "0"))
  (SETQ DAS (substr AP (- lng 7) 2))
  (SETQ CAS (substr AP (- lng 5) 6))
  (SETQ SUPHAS (STRCAT HAS "-" DAS "-" CAS " HAS"))
  (SETQ X (CAR PTO))
  (SETQ X2 (/ X 100))
  (SETQ X2 (RTOS X2 2 0))
  (setq x2 (rtos (* (atof x2) 100) 2 0))
  (SETQ Y (CADR PTO))
  (SETQ Y2 (/ Y 100))
  (SETQ Y2 (RTOS Y2 2 0))
  (setq y2 (rtos (* (atof y2) 100) 2 0))
  (SETQ X (RTOS X 2 4))
  (SETQ Y (RTOS Y 2 4))
  (command "insert" (strcat ruta "BLOCKS\\CRUCES.dwg") (strcat x2 "," y2) "" "" "")
  (command "explode" (entlast) "" "CHANGE" "P" "" "P" "LA" "CRUCES" "")
  (command "insert" (strcat ruta "BLOCKS\\lx.dwg") (strcat x2 "," (rtos (+ (atof y) 159.229) 2 3)) "" "" "")
  (command "insert" (strcat ruta "BLOCKS\\textc.dwg") (strcat x2 "," (rtos (+ (atof y) 159.229) 2 3)) "2" "" "")
  (COMMAND "EXPLODE" (ENTLAST) "" "CHANGE" "P" "" "P" "LA" "TEXTOS" "" "CHANGE" "P" "" "" "" "" "" "" X2)
  (command "insert" (strcat ruta "BLOCKS\\lx.dwg") (strcat (rtos (+ (atof X2) 100) 2 0) "," (rtos (+ (atof y) 159.229) 2 3)) "" "" "")
  (command "insert" (strcat ruta "BLOCKS\\textc.dwg") (strcat (rtos (+ (atof X2) 100) 2 0) "," (rtos (+ (atof y) 159.229) 2 3)) "2" "" "")
  (COMMAND "EXPLODE" (ENTLAST) "" "CHANGE" "P" "" "P" "LA" "TEXTOS" "" "CHANGE" "P" "" "" "" "" "" "" (rtos (+ (atof X2) 100) 2 0))
  (command "insert" (strcat ruta "BLOCKS\\lx.dwg") (strcat (rtos (+ (atof X2) 200) 2 0) "," (rtos (+ (atof y) 159.229) 2 3)) "" "" "")
  (command "insert" (strcat ruta "BLOCKS\\textc.dwg") (strcat (rtos (+ (atof X2) 200) 2 0) "," (rtos (+ (atof y) 159.229) 2 3)) "2" "" "")
  (COMMAND "EXPLODE" (ENTLAST) "" "CHANGE" "P" "" "P" "LA" "TEXTOS" "" "CHANGE" "P" "" "" "" "" "" "" (rtos (+ (atof X2) 200) 2 0))
  (command "insert" (strcat ruta "BLOCKS\\lx.dwg") (strcat (rtos (+ (atof X2) 300) 2 0) "," (rtos (+ (atof y) 159.229) 2 3)) "" "" "")
  (command "insert" (strcat ruta "BLOCKS\\textc.dwg") (strcat (rtos (+ (atof X2) 300) 2 0) "," (rtos (+ (atof y) 159.229) 2 3)) "2" "" "")
  (COMMAND "EXPLODE" (ENTLAST) "" "CHANGE" "P" "" "P" "LA" "TEXTOS" "" "CHANGE" "P" "" "" "" "" "" "" (rtos (+ (atof X2) 300) 2 0))
  (command "insert" (strcat ruta "BLOCKS\\lx.dwg") (strcat (rtos (- (atof X2) 100) 2 0) "," (rtos (+ (atof y) 159.229) 2 3)) "" "" "")
  (command "insert" (strcat ruta "BLOCKS\\textc.dwg") (strcat (rtos (- (atof X2) 100) 2 0) "," (rtos (+ (atof y) 159.229) 2 3)) "2" "" "")
  (COMMAND "EXPLODE" (ENTLAST) "" "CHANGE" "P" "" "P" "LA" "TEXTOS" "" "CHANGE" "P" "" "" "" "" "" "" (rtos (- (atof X2) 100) 2 0))
  (command "insert" (strcat ruta "BLOCKS\\lx.dwg") (strcat (rtos (- (atof X2) 200) 2 0) "," (rtos (+ (atof y) 159.229) 2 3)) "" "" "")
  (command "insert" (strcat ruta "BLOCKS\\textc.dwg") (strcat (rtos (- (atof X2) 200) 2 0) "," (rtos (+ (atof y) 159.229) 2 3)) "2" "" "")
  (COMMAND "EXPLODE" (ENTLAST) "" "CHANGE" "P" "" "P" "LA" "TEXTOS" "" "CHANGE" "P" "" "" "" "" "" "" (rtos (- (atof X2) 200) 2 0))
  (command "insert" (strcat ruta "BLOCKS\\lx.dwg") (strcat (rtos (- (atof X2) 300) 2 0) "," (rtos (+ (atof y) 159.229) 2 3)) "" "" "")
  (command "insert" (strcat ruta "BLOCKS\\textc.dwg") (strcat (rtos (- (atof X2) 300) 2 0) "," (rtos (+ (atof y) 159.229) 2 3)) "2" "" "")
  (COMMAND "EXPLODE" (ENTLAST) "" "CHANGE" "P" "" "P" "LA" "TEXTOS" "" "CHANGE" "P" "" "" "" "" "" "" (rtos (- (atof X2) 300) 2 0))

  (command "insert" (strcat ruta "BLOCKS\\ly.dwg") (strcat (rtos (- (atof X) 246.274) 2 0) "," (rtos (+ (atof y2) 300) 2 0)) "" "" "")
  (command "insert" (strcat ruta "BLOCKS\\texto.dwg") (strcat (rtos (- (atof X) 246.274) 2 0) "," (rtos (+ (atof y2) 300) 2 0)) "2" "" "")
  (COMMAND "EXPLODE" (ENTLAST) "" "CHANGE" "P" "" "P" "LA" "TEXTOS" "" "CHANGE" "P" "" "" "" "" "" "" (rtos (+ (atof Y2) 300) 2 0))
  (command "insert" (strcat ruta "BLOCKS\\ly.dwg") (strcat (rtos (- (atof X) 246.274) 2 0) "," (rtos (+ (atof y2) 200) 2 0)) "" "" "")
  (command "insert" (strcat ruta "BLOCKS\\texto.dwg") (strcat (rtos (- (atof X) 246.274) 2 0) "," (rtos (+ (atof y2) 200) 2 0)) "2" "" "")
  (COMMAND "EXPLODE" (ENTLAST) "" "CHANGE" "P" "" "P" "LA" "TEXTOS" "" "CHANGE" "P" "" "" "" "" "" "" (rtos (+ (atof Y2) 200) 2 0))
  (command "insert" (strcat ruta "BLOCKS\\ly.dwg") (strcat (rtos (- (atof X) 246.274) 2 0) "," (rtos (+ (atof y2) 100) 2 0)) "" "" "")
  (command "insert" (strcat ruta "BLOCKS\\texto.dwg") (strcat (rtos (- (atof X) 246.274) 2 0) "," (rtos (+ (atof y2) 100) 2 0)) "2" "" "")
  (COMMAND "EXPLODE" (ENTLAST) "" "CHANGE" "P" "" "P" "LA" "TEXTOS" "" "CHANGE" "P" "" "" "" "" "" "" (rtos (+ (atof Y2) 100) 2 0))
  (command "insert" (strcat ruta "BLOCKS\\ly.dwg") (strcat (rtos (- (atof X) 246.274) 2 0) "," Y2) "" "" "")
  (command "insert" (strcat ruta "BLOCKS\\texto.dwg") (strcat (rtos (- (atof X) 246.274) 2 0) "," Y2) "2" "" "")
  (COMMAND "EXPLODE" (ENTLAST) "" "CHANGE" "P" "" "P" "LA" "TEXTOS" "" "CHANGE" "P" "" "" "" "" "" "" Y2)
  (command "insert" (strcat ruta "BLOCKS\\ly.dwg") (strcat (rtos (- (atof X) 246.274) 2 0) "," (rtos (- (atof y2) 100) 2 0)) "" "" "")
  (command "insert" (strcat ruta "BLOCKS\\texto.dwg") (strcat (rtos (- (atof X) 246.274) 2 0) "," (rtos (- (atof y2) 100) 2 0)) "2" "" "")
  (COMMAND "EXPLODE" (ENTLAST) "" "CHANGE" "P" "" "P" "LA" "TEXTOS" "" "CHANGE" "P" "" "" "" "" "" "" (rtos (- (atof Y2) 100) 2 0))
  (command "insert" (strcat ruta "BLOCKS\\ly.dwg") (strcat (rtos (- (atof X) 246.274) 2 0) "," (rtos (- (atof y2) 200) 2 0)) "" "" "")
  (command "insert" (strcat ruta "BLOCKS\\texto.dwg") (strcat (rtos (- (atof X) 246.274) 2 0) "," (rtos (- (atof y2) 200) 2 0)) "2" "" "")
  (COMMAND "EXPLODE" (ENTLAST) "" "CHANGE" "P" "" "P" "LA" "TEXTOS" "" "CHANGE" "P" "" "" "" "" "" "" (rtos (- (atof Y2) 200) 2 0))
  (command "insert" (strcat ruta "BLOCKS\\ly.dwg") (strcat (rtos (- (atof X) 246.274) 2 0) "," (rtos (- (atof y2) 300) 2 0)) "" "" "")
  (command "insert" (strcat ruta "BLOCKS\\texto.dwg") (strcat (rtos (- (atof X) 246.274) 2 0) "," (rtos (- (atof y2) 300) 2 0)) "2" "" "")
  (COMMAND "EXPLODE" (ENTLAST) "" "CHANGE" "P" "" "P" "LA" "TEXTOS" "" "CHANGE" "P" "" "" "" "" "" "" (rtos (- (atof Y2) 300) 2 0))

  (SETQ GPOP (SSADD))                                                                               ;seleciona nomnum
  (SETQ GPOP (SSGET "X" '((2 . "NOMNUM"))))
  (IF (/= (SSLENGTH GPOP) 1)
   (PROGN
     (ALERT "hay dos blocks con attributos de nombre y numero de lote")
     (setq ex (car (entsel "Selecciona el block fuente" )))
   )
   (SETQ EX (SSNAME GPOP 0))
  )
  (setq ptoX (cdr (assoc 10 (entget Ex))))
;  (setq no-lt (busatr ex "NO-LOTE"))
  (setq name (getvar "dwgname"))
  (SETQ LNG (STRLEN NAME))
  (SETQ NO-LT (SUBSTR NAME 1 (- LNG 4)))
  (IF (= NO-LT NIL)
    (setq no-lt (busatr ex "NO_LOTE"))
  )
  (setq nombrex (busatr ex "NOMBRE"))

  (COMMAND "LAYER" "s" "0" "")
  (command "insert" (strcat ruta "BLOCKS\\texto.dwg") (strcat (rtos (+ (atof X) 164.452) 2 3) "," (rtos (- (atof y) 48.113) 2 3)) "1.3" "" "")
  (COMMAND "EXPLODE" (ENTLAST) "" "CHANGE" "P" "" "" "" "" "" "" (STRCAT "PROPIETARIO " NOMBREX))
  (command "insert" (strcat ruta "BLOCKS\\texto.dwg") (strcat (rtos (+ (atof X) 164.452) 2 3) "," (rtos (- (atof y) 50.792) 2 3)) "1.3" "" "")
  (COMMAND "EXPLODE" (ENTLAST) "" "CHANGE" "P" "" "" "" "" "" "" (STRCAT "NUMERO DE TERRENO " NO-LT))
  (command "insert" (strcat ruta "BLOCKS\\texto.dwg") (strcat (rtos (+ (atof X) 164.452) 2 3) "," (rtos (- (atof y) 53.674) 2 3)) "1.3" "" "")
  (COMMAND "EXPLODE" (ENTLAST) "" "CHANGE" "P" "" "" "" "" "" "" (STRCAT "SUPERFICIE " SUPHAS))
  (command "insert" (strcat ruta "BLOCKS\\textC.dwg") (strcat (rtos (+ (atof X) 189.729) 2 3) "," (rtos (- (atof y) 128.340) 2 3)) "1.3" "" "")
  (COMMAND "EXPLODE" (ENTLAST) "" "CHANGE" "P" "" "" "" "" "" "" (STRCAT "TERRENO: " NO-LT "  SUP. " SUPHAS))
  (command "insert" (strcat ruta "BLOCKS\\textO.dwg") (strcat (rtos (+ (atof X) 228.249) 2 3) "," (rtos (- (atof y) 124.466) 2 3)) "0.95" "" "")
  (COMMAND "EXPLODE" (ENTLAST) "" "CHANGE" "P" "" "" "" "" "" "" (STRCAT "CHP-MICH-" NO-LT))
  (IF (= (SUBSTR NAME 1 2) "DL") (SETQ POTR "LAS DELICIAS"))
  (IF (= (SUBSTR NAME 1 2) "FR") (SETQ POTR "LOS FRIJOLES"))
  (IF (= (SUBSTR NAME 1 3) "SI2") (SETQ POTR "SAN IGNACIO ORIENTE"))
  (IF (= (SUBSTR NAME 1 3) "RB2") (SETQ POTR "RAYAS BLANCAS ORIENTE"))
  (IF (= (SUBSTR NAME 1 3) "GA") (SETQ POTR "LA GALERA"))
  (command "insert" (strcat ruta "BLOCKS\\textC.dwg") (strcat (rtos (+ (atof X) 189.729) 2 3) "," (rtos (- (atof y) 125.935) 2 3)) "1.3" "" "")
  (COMMAND "EXPLODE" (ENTLAST) "" "CHANGE" "P" "" "" "" "" "" "" (STRCAT "POTRERO " POTR))


  (SETQ GPORET (SSGET "X" '((8 . "CRUCES"))))
  (SETQ GPOLIN (SSGET "X" '((8 . "LINEALMP"))))
  (SETQ GPOPROV (SSGET "X" '((8 . "TEXTOS"))))
  (SETQ GPOlx (SSGET "X" '((2 . "lx"))))
  (SETQ GPOly (SSGET "X" '((2 . "ly"))))
  (SETQ LINEA (SSNAME GPOLIN 0))
  (SETQ PROV 1)
  (SETQ VER1 (VERTICE LINEA prov))
  (COMMAND "ERASE" GPORET GPOPROV gpoly gpolx "R" "CP")
  (WHILE VER1
     (IF (/= VER1 NIL)
      (progn
        (SETQ Y (CADR ver1))
        (SETQ Y (RTOS Y 2 3))
        (SETQ X (CAR ver1))
        (SETQ X (RTOS X 2 3))
        (COMMAND (STRCAT X "," Y))
      )
      (COMMAND "")
     )
     (SETQ PROV (1+ PROV))
     (SETQ VER1 (vertice LINEA prov))
  )
  (command "" "")
  (setq gpoar (ssget "X" '((2 . "corten") (41 . 1.6))))
  (setq gpoar2 (ssget "X" '((2 . "terraplenn") (41 . 1.6))))
        (setq ele2 0)
        (setq E (ssname gpoar ele2))
        (while E
          (setq XYZ (cdr (assoc 10 (entget E))))
          (command "SCALE" e "" XYZ "1.5")
          (setq ele2 (1+ ele2))
          (setq E (ssname gpoar ele2))
        )
        (setq ele2 0)
        (setq E (ssname gpoar2 ele2))
        (while E
          (setq XYZ (cdr (assoc 10 (entget E))))
          (command "SCALE" e "" XYZ "1.5")
          (setq ele2 (1+ ele2))
          (setq E (ssname gpoar2 ele2))
        )
  (COMMAND "ERASE" LINEA "")
  (command "attdisp" "no")
  (command "purge" "all" "" "n")
  (command "purge" "all" "" "n")

  (setvar "osmode" os)
  (COMMAND "ZOOM" "e")
  (C:LPC)
)

(defun SUMA (punto xx yy)
  (setq x (car punto))
  (setq y (car (cdr punto)))
  (setq xxx (+ x xx))
  (setq yyy (+ y yy))
  (list xxx yyy)
)
