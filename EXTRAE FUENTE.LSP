(defun C:CAPT ()
    (setq ARCH (open (STRCAT "C:\\f\\datosf.TXT") "w"))
    (setq texto (car (entsel "Selecciona el texto: ")))
    (SETQ CONT 1)
    (REPEAT 255
      (COMMAND "CHANGE" texto "" "" "" "" "" "" (CHR CONT))
      (COMMAND "ZOOM" "C" "0,0" "240.00")
      (SETQ F (GETSTRING "LISTO EL ZOOM?"))
      (COMMAND "MSLIDE" (STRCAT "C:\\F\\L" (ITOA CONT)))
      (SETQ CONT (1+ CONT))
      (setq pantalla (getvar "SCREENSIZE"))
      (setq xp (car pantalla))
      (setq yp (cadr pantalla))
      (SETQ LINEA (STRCAT (rtos xp) "," (rtos yp)))
      (write-line LINEA arcH)
    )
    (close arch)
   (alert "termine")
)

(defun C:dt ()
    (setq texto (car (entsel "Selecciona el texto: ")))
    (SETQ CONT 1)
    (setq textol "")
    (REPEAT 255
      (setq textol (strcat textol (CHR CONT)))
      (SETQ CONT (1+ CONT))
    )
    (COMMAND "CHANGE" texto "" "" "" "" "" "" textol)
)
