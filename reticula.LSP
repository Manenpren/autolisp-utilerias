(DEFUN C:reticula ()
  (COMMAND "UNDO" "M")
  (C:LIBRERIA "UTM-GEO")
  (C:LIBRERIA "GEO-UTM")
  (C:LIBRERIA "DECIMALTOSEXAGESIMAL")
  (SETQ ZONA (GETINT "\n ZONA HORARIA ? "))
  (SETQ ESCALA (GETINT "\n ESCALA DEL PLANO ? "))
  (SETQ SEPRET (GETREAL "\n SEPARACION DE RETICULA EN SEGUNDOS "))
  (SETQ SEPRET (/ (/ SEPRET 60) 60))
  (setq PUNTOX (getpoint " PUNTO DE INSERCION DEL PLANO : "))
  (SETQ XV (ATOF (RTOS (CAR puntoX) 2 12)))
  (SETQ YV (ATOF (RTOS (CADR puntoX) 2 12)))
  (setq PUNTO (getpoint " 1ra Esquina : "))
  (SETQ X1 (ATOF (RTOS (CAR punto) 2 12)))
  (SETQ Y1 (ATOF (RTOS (CADR punto) 2 12)))
  (setq PUNTO2 (getpoint " 2da Esquina : "))
  (SETQ X2 (ATOF (RTOS (CAR punto2) 2 12)))
  (SETQ Y2 (ATOF (RTOS (CADR punto2) 2 12)))
  (IF (> X1 X2)
    (PROGN
      (SETQ XMAYOR X1)
      (SETQ XMENOR X2)
    )
    (PROGN
      (SETQ XMAYOR X2)
      (SETQ XMENOR X1)
    )
  )
  (IF (> Y1 Y2)
    (PROGN
      (SETQ YMAYOR Y1)
      (SETQ YMENOR Y2)
    )
    (PROGN
      (SETQ YMAYOR Y2)
      (SETQ YMENOR Y1)
    )
  )
  (SETQ PUNTO (LIST XMAYOR YMAYOR))
  (SETQ PUNTO2 (LIST XMENOR YMENOR))
  (SETQ PUNTOGEO (UTM-GEO PUNTO ZONA))
  (SETQ LAT (CAR puntoGEO))
  (SETQ LONG (CADR puntoGEO))
  (SETQ PUNTOGEO2 (UTM-GEO PUNTO2 ZONA))
  (SETQ LAT2 (CAR puntoGEO2))
  (SETQ LONG2 (CADR puntoGEO2))
  (SETQ LATINI (RTOS (ABS (/ LAT2 SEPRET)) 2 0))
  (SETQ LONGINI (RTOS (ABS (/ LONG2 SEPRET)) 2 0))
  (SETQ LATFIN (RTOS (ABS (/ LAT SEPRET)) 2 0))
  (SETQ LONGFIN (RTOS (ABS (/ LONG SEPRET)) 2 0))

  (SETQ CONT2 0)
  (REPEAT (- (ATOI LATini) (ATOI LATfin) -1)
   (SETQ CONT1 0)
   (REPEAT (- (ATOI LATini) (ATOI LATfin) -1)
    (SETQ PGEO (LIST (* (- (ATOI LATINI) CONT2) SEPRET -1) (* (+ (ATOI LONGINI) CONT1) SEPRET)))
    (SETQ XYZ (GEO-UTM PGEO))
    (SETQ PGEO (LIST (* (- (ATOI LATINI) CONT2) SEPRET -1) LONG))
    (SETQ XYZ2 (GEO-UTM PGEO))
    (SETQ PGEO (LIST LAT (* (+ (ATOI LONGINI) CONT1) SEPRET)))
    (SETQ XYZ3 (GEO-UTM PGEO))
    (SETQ PGEO (LIST (* (- (ATOI LATINI) CONT2) SEPRET -1) LONG))
    (SETQ XYZ4 (GEO-UTM PGEO))
    (SETQ PGEO (LIST LAT (* (+ (ATOI LONGINI) CONT1) SEPRET)))
    (SETQ XYZ5 (GEO-UTM PGEO))

    (COMMAND "INSERT" (STRCAT RUTA "BLOCKS\\CRUZGPS.dwg") XYZ ESCALA "" "")
    (COMMAND "CHANGE" (ENTLAST) "" "P" "LA" "PP" "")
    (IF (= CONT2 0) 
      (PROGN
        (COMMAND "INSERT" (STRCAT RUTA "BLOCKS\\LUTM2-2.dwg") XYZ5 ESCALA "" "")
        (COMMAND "EXPLODE" (ENTLAST) "" "CHANGE" "P" "" "P" "LA" "PP" "")
        (COMMAND "INSERT" (STRCAT RUTA "BLOCKS\\TEXTUTM2-2.dwg") XYZ3 ESCALA "" "")
        (COMMAND "EXPLODE" (ENTLAST) "" "CHANGE" "P" "" "P" "LA" "PP" "" "CHANGE" "P" "" "" "" "" "" "" (DECSEXA (* (+ (ATOI LONGINI) CONT1) SEPRET)))
      )
    )
    (IF (= CONT1 0) 
      (PROGN
        (COMMAND "INSERT" (STRCAT RUTA "BLOCKS\\LUTM-2.dwg") XYZ4 ESCALA "" "")
        (COMMAND "EXPLODE" (ENTLAST) "" "CHANGE" "P" "" "P" "LA" "PP" "")
        (COMMAND "INSERT" (STRCAT RUTA "BLOCKS\\TEXTUTM-2.dwg") XYZ2 ESCALA "" "")
        (COMMAND "EXPLODE" (ENTLAST) "" "CHANGE" "P" "" "P" "LA" "PP" "" "CHANGE" "P" "" "" "" "" "" "" (DECSEXA (* (- (ATOI LATINI) CONT2) SEPRET)))
      )
    )
    (SETQ CONT1 (1+ CONT1))
   )
   (SETQ CONT2 (1+ CONT2))
  )
)

(DEFUN C:CONVERG ()
  (C:LIBRERIA "CONVERGENCIAa")
  (SETQ XYZ (GETPOINT "\n PUNTO ? "))
  (SETQ ZONA (GETINT "\n ZONA HORARIA ? "))
  (SETQ R (CONVERGENCIAa XYZ ZONA))
)
