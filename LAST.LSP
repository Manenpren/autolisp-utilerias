(defun C:P1 ()
    (setq F (getint "Numero de repeticiones"))
    (setq block (car (entsel "block donde comenzar: ")))
    (setq LAYER (cdr (assoc 8 (entget block))))
    (setq escala (cdr (assoc 41 (entget block))))
    (setq ancho (getreal "Ancho de los lotes: "))
    (setq pun (cdr (getpoint "direccion 1 : ")))
    (setq pun2 (cdr (getpoint "direccion 2 : ")))
    (setq ang (angle pun pun2))
    (command "snap" "ro" pun (angtos ang 1 4))
    (WHILE f
        (command "array" block "" "r" "" "2" ancho)
        (setq block (entlast))
        (setq xy (cdr (assoc 10 (entget block))))
        (command "erase" block "")
        (COMMAND "ZOOM" "C" XY "25")
        (COMMAND "BPOLY" xy "")
        (setq lin (entlast))
        (command "AREA" "OB" lin "")
        (SETQ AREA (RTOS (GETVAR "AREA") 2 3))
        (command "erase" lin "")
        (COMMAND "INSERT" "NOMAR" xy escala "" "" "M7-3b" AREA)
        (setq block (entlast))
        (command "change" block "" "p" "la" layer "")
    )
    (setq sp())
)

(DEFUN SP ()
    (command "snap" "ro" "0,0" "0")
    (command "snap" "off")
)
