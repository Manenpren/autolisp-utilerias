(DEFUN C:ASOC ()
  (setq OBJ (car (entsel "\n Selecciona EL OBJETO a procesar: ")))
  (SETQ R 0)
  (SETQ ASOCIA (entget OBJ))
  (REPEAT 10000
    (SETQ ASO (cdr (assoc R ASOCIA)))
    (IF (/= ASO NIL)
     (PROGN
      (PRINT R)
      (PRINT ASO)
     )
    )
    (SETQ R (+ R 1))
  )
  (PROMPT ASOCIA)
)

(DEFUN C:ASOC2 ()
  (setq OBJ (car (entsel "\n Selecciona EL OBJETO a procesar: ")))
  (SETQ R 0)
  (SETQ OBJ (ENTNEXT OBJ))
  (SETQ ASOCIA (entget OBJ))
  (REPEAT 10000
    (SETQ ASO (cdr (assoc R ASOCIA)))
    (IF (/= ASO NIL)
     (PROGN
      (PRINT R)
      (PRINT ASO)
     )
    )
    (SETQ R (+ R 1))
  )
  (PROMPT ASOCIA)
)

(DEFUN C:ASOC3 ()
  (setq OBJ (car (entsel "\n Selecciona EL OBJETO a procesar: ")))
  (SETQ R 0)
  (SETQ OBJ (ENTNEXT OBJ))
  (SETQ OBJ (ENTNEXT OBJ))
  (SETQ ASOCIA (entget OBJ))
  (REPEAT 10000
    (SETQ ASO (cdr (assoc R ASOCIA)))
    (IF (/= ASO NIL)
     (PROGN
      (PRINT R)
      (PRINT ASO)
     )
    )
    (SETQ R (+ R 1))
  )
  (PROMPT ASOCIA)
)
