(defun C:creg ()
  (C:LIBRERIA "BUSCA VALOR DE ATRIBUTO")
  (setq bl1 (car (entsel "Selecciona el block de elevaciones : ")))
  (setq bl2 (car (entsel "Selecciona el block a modificar : ")))
  (setq eleva (busatr BL1 "ELEVACION"))
  (setq eleva (atof eleva))
  (SETQ XYZ (cdr (assoc 10 (entget BL1))))
  (SETQ XYZ2 (cdr (assoc 10 (entget BL2))))
  (SETQ DIST (DISTANCE XYZ XYZ2))
  (SETQ ELEVF (- ELEVA (* DIST 0.001)))
  (SETQ ENTP (ENTNEXT BL2)) 
  (COMMAND "ATTEDIT" "" "" "" "" ENTP "V" "R" (rtos (1- ELEVF) 2 3) "") 
  (SETQ ENTP (ENTNEXT entp))
  (COMMAND "ATTEDIT" "" "" "" "" ENTP "V" "R" (rtos elevF 2 3) "") 
  (SETQ ENTP (ENTNEXT entp))
  (COMMAND "ATTEDIT" "" "" "" "" ENTP "V" "R" "1.000" "") 
)
