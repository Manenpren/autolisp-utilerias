(defun C:ex3d ()
  (setq e (car (entsel "\n Selecciona la malla exportar")))
  (setq NomArch (getfiled "ARCHIVO A CREAR " "*." "CSV" 19))
  (if (= nomarch nil) (exit))
  (setq Arch (open NomArch "w"))
  (command "explode" e "")
  (setq gpomalla (ssget "p"))
  (setq e (ssname gpomalla 0))
  (setq cont 1)
  (while e
    (setq punto (cdr (assoc 10 (entget e))))
    (SETQ X (CAR PUNTO))
    (SETQ Y (CADR PUNTO))
    (SETQ z (CADDR PUNTO))
    (setq xyz1 (strcat (rtos x) "," (rtos y) "," (rtos z) ",1,z"))
    (setq punto (cdr (assoc 11 (entget e))))
    (SETQ X (CAR PUNTO))
    (SETQ Y (CADR PUNTO))
    (SETQ z (CADDR PUNTO))
    (setq xyz2 (strcat (rtos x) "," (rtos y) "," (rtos z) ",1,z"))
    (setq punto (cdr (assoc 12 (entget e))))
    (SETQ X (CAR PUNTO))
    (SETQ Y (CADR PUNTO))
    (SETQ z (CADDR PUNTO))
    (setq xyz3 (strcat (rtos x) "," (rtos y) "," (rtos z) ",1,z"))
    (write-line xyz1 Arch)
    (write-line xyz2 Arch)
    (write-line xyz3 Arch)
    (setq e (ssname gpomalla cont))
    (setq cont (1+ cont))
  )
  (close arch)
)
