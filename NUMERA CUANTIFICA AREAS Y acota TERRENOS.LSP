(DEFUN SUMA (P VX VY)
  (SETQ X (CAR P))
  (SETQ Y (CAR (CDR P)))
  (LIST (+ X VX) (+ Y vy) (LAST P))
)

(defun c:NUM ()
  (COMMAND "UNDO" "M")
  (COMMAND "LUNITS" 2)
  (COMMAND "LUPREC" 7)
  (COMMAND "AUNITS" 0)
  (COMMAND "AUPREC" 4)
  (COMMAND "ANGDIR" 0)
  (COMMAND "ANGBASE" 0.0)
  (COMMAND "DIMZIN" 0)  (setq inicio (getint "\n inicio: "))
  (setq man (getint "\n manzana: "))
  (setq escALA (getreal "\n Escala del texto: "))
  (setq PUNTO (getpoint " DAME EL CENTRO DEL AREA : "))
  (WHILE PUNTO
    (setq arch (open "lintop" "w"))
    (COMMAND "BPOLY" PUNTO "")
    (setq LIN (entlast))
    (command "AREA" "OB" LIN "")
    (SETQ AREA (RTOS (GETVAR "AREA") 2 3))
    (setq linea (ENTLAST)) 

    (COMMAND "INSERT" (STRCAT RUTA "BLOCKS\\NOMAR") PUNTO escALA "" "" (strcat "M" (itoa Man) "-L" (itoa inicio)) AREA)
    (SETQ INICIO (1+ INICIO))
;  (setq TipEnt (cdr (assoc 0 (entget linea)))) 
;  (setq tipent (strcase tipent))
;  (if (and (/= "LWPOLYLINE" TipEnt) (/= "LINE" TipEnt) (/= "ARC" TipEnt))
;    (alert "La entidad que seleccionaste no es una linea")
;  ) 
  (command "copy" linea "" "0,0" "0,0")
  (SETQ PRV (cdr (assoc 0 (entget linea))))
  (SETQ PRV (STRCASE PRV))
  (IF (=  PRV "LWPOLYLINE") 
    (PROGN
      (command "explode" (entlast) "")
      (setq gpoacot (ssadd))
      (setq gpoacot (ssget "p"))
    )
    (SETQ GPOACOt (SSADD LINEA))
  )
  (SETQ E (SSNAME GPOACOT 0))
  (SETQ T1 1)
  (setq cont 0)
  (WHILE E
    (SETQ PRV (cdr (assoc 0 (entget E))))
    (SETQ PRV (STRCASE PRV))
    (IF (= PRV "ARC")
      (PROGN
        (SETQ RADIO (cdr (assoc 40 (entget e))))
        (SETQ RADIOx (cdr (assoc 10 (entget e))))
        (SETQ Yr (CADR radiox))
        (SETQ Xr (CAR radiox))
        (SETQ ANGINI (cdr (assoc 50 (entget e))))
        (SETQ ANGF (cdr (assoc 51 (entget e))))
        (setq xc1 (+ xr (* radio (cos angini))))
        (setq yc1 (+ yr (* radio (sin angini))))
        (setq xc2 (+ xr (* radio (cos angf))))
        (setq yc2 (+ yr (* radio (sin angf))))
        (IF (> XC2 XC1)
          (PROGN
            (setq xyz (list xc1 yc1))
            (setq xyz2 (list xc2 yc2))
          )
          (PROGN
            (setq xyz2 (list xc1 yc1))
            (setq xyz (list xc2 yc2))
          )
        )
        (IF (< ANGINI ANGF)
          (PROGN
            (SETQ DIF (- ANGF ANGINI))
            (setq ang2 (+ angini (/ dif 2)))
          )
          (PROGN
            (SETQ ANGF (+ ANGF 6.28318))
            (SETQ DIF (- ANGF ANGINI))
            (setq ang2 (+ angini (/ dif 2)))
          )
        )
        (setq xc3 (+ xr (* radio (cos ang2))))
        (setq yc3 (+ yr (* radio (sin ang2))))
        (SETQ DISTANCIA (* RADIO DIF))
      )
      (progn
        (SETQ xyz (cdr (assoc 10 (entget e))))
        (SETQ xyz2 (cdr (assoc 11 (entget e))))
        (setq distancia (distance xyz xyz2))
      )
    )
  (setq distancia2 (distance xyz xyz2))
      (setq ang (angle xyz xyz2))
      (setq ang (* 180 (/ ang pi)))
      (setq angxx ang)
      (setq xyz3 (polar XYZ (angle XYZ XYZ2) (/ DISTANCIA2 2)))
      (SETQ ANGMOD 0)
      (SETQ NOMBREBL "BLOCKS\\COTA")
      (if (AND (> angxx 180) (< angxx 270))
        (progn
          (setq angxx (- angxx 180))
          (SETQ NOMBREBL "BLOCKS\\COTA2")
          (SETQ ANGMOD 1)
;          (IF (= PRV "ARC") (SETQ NOMBREBL "BLOCKS\\COTA"))
        )
      )
      (if (AND (> angxx 90) (< angxx 180) (= ANGMOD 0))
        (progn
          (setq angxx (+ angxx 180))
          (SETQ NOMBREBL "BLOCKS\\COTA2")
          (SETQ ANGMOD 1)
;          (IF (= PRV "ARC") (SETQ NOMBREBL "BLOCKS\\COTA"))
        )
      )
      (if (AND (OR (> angxx 270) (< angxx 91)) (= ANGMOD 0))
        (SETQ NOMBREBL "BLOCKS\\COTA")
      )
  (IF (= PRV "ARC")
    (progn 
      (command "INSERT" (STRCAT RUTA NOMBREBL) (list xc3 yc3) escala "" angXX "" "")
    )
    (progn 
      (command "INSERT" (STRCAT RUTA NOMBREBL) xyz3 escala "" ANGXX "" "")
    )
  )
  (SETQ ENTP (ENTLAST))
  (SETQ ENTP (ENTNEXT ENTP))
  (COMMAND "ATTEDIT" "" "" "" "" ENTP "V" "R" (rtos distancia 2 3) "")
  (SETQ CONT (1+ CONT))
  (SETQ E (SSNAME GPOACOT cont))
  )
  (command "erase" gpoacot "")
  (setq PUNTO (getpoint " DAME EL CENTRO DEL AREA : "))
  (command "erase" lin "")
  );WHILE
)
