(defun c:attrib ()
 (setq arcdes (getfiled "ARCHIVO DE Descarga" "C:\\TOPOGRAF" "CSV" 19))
 (SETQ f1 (OPEN arcdes "a"))
 (REPEAT 10000
  (setq PROV (CAR (ENTSEL "SELECCIONA BLOCK")))
  (setq NOMBLO (cdr (assoc 2 (entget PROV))))
  (COMMAND "INSERT" NOMBLO "0,0" "" "" "")
  (COMMAND "EXPLODE" "L" "")
  (SETQ GPOA (SSGET "P"))
  (SETQ P 0)
  (WHILE (/= (cdr (assoc 0 (entget PROV))) "TEXT")
    (SETQ PROV (SSNAME GPOA P))
    (SETQ P (1+ P))
  )
  (setq XY (cdr (assoc 10 (entget PROV))))
  (COMMAND "ZOOM" "C" XY "60")
  (SETQ CADENA (CAR (ENTSEL "SELECCIONA EL CADENAMIENTO")))
  (SETQ CORTE (CAR (ENTSEL "SELECCIONA EL CORTE")))
  (SETQ TERRAP (CAR (ENTSEL "SELECCIONA EL TERAPLEN")))
  (setq CADENAMIENTO (cdr (assoc 1 (entget PROV))))
  (IF (/= CORTE NIL)
   (PROGN
    (SETQ E (ENTNEXT CORTE))
    (SETQ E (ENTNEXT E)) 
    (setq CORTEF (cdr (assoc 1 (entget E))))
   )
   (SETQ CORTEF "")
  )
  (IF (/= TERRAP NIL)
   (PROGN
    (SETQ E (ENTNEXT TERRAP))
    (SETQ E (ENTNEXT E)) 
    (setq TERRAPF (cdr (assoc 1 (entget E))))
   )
   (SETQ TERRAPF "")
  )
  (WRITE-LINE (STRCAT CADENAMIENTO "," CORTEF "," TERRAPF) F1)
  (COMMAND "ERASE" GPOA "")
  (COMMAND "ZOOM" "P")
 )
 (CLOSE F1)
)
