(DEFUN C:INTER2 ()
    (COMMAND "UNDO" "M")
    (C:LIBRERIA "busca block en base de datos")
    (C:LIBRERIA "BUSCA VALOR DE ATRIBUTO")
    (SETQ OPCIONESOS (GETVAR "OSMODE"))
    (command "osnap" "none")
    (SETQ VALIDA (SBLBD "X"))
    (IF (/= "S" VALIDA) (SETQ VALIDA (SBLBD "x")))
    (If (/= VALIDA "S") 
      (PROGN 
       (COMMAND "INSERT" (STRCAT RUTA "BLOCKS\\X.DWG") "0,0" "" "" "" "")
       (COMMAND "ERASE" (ENTLAST) "")
      )
    )
    (setq block (car (entsel "primer block : ")))
    (setq block2 (car (entsel "segundo block : ")))
    (setq xyz (cdr (assoc 10 (entget block))))
    (setq xyz2 (cdr (assoc 10 (entget block2))))
    (SETQ DISTA (DISTANCE XYZ XYZ2))
    (SETQ NDIV (1+ (FIX (/ DISTA 2))))
    (SETQ Y (CADR xyz))
    (SETQ Y (RTOS Y 2 5))
    (SETQ X (CAR xyz))
    (SETQ X (RTOS X 2 5))
    (SETQ Y2 (CADR xyz2))
    (SETQ Y2 (RTOS Y2 2 5))
    (SETQ X2 (CAR xyz2))
    (SETQ X2 (RTOS X2 2 5))
    (setq elev1 (busatr block "ELEV"))
    (setq elev2 (busatr block2 "ELEV"))
    (command "line" ".xy" (strcat x "," y) elev1 ".xy" (strcat x2 "," y2) elev2 "")
    (SETQ LIN (ENTLAST))
    (COMMAND "DIVIDE" LIN "B" "X" "" NDIV)
    (setq gpoin (ssadd))
    (setq gpoin (ssget "P"))
    (COMMAND "ERASE" LIN "")
    (setq e (ssname gpoin 0))
    (setq t1 0)
    (while e
      (setq xyz2 (cdr (assoc 10 (entget e))))
      (SETQ z (CADdR xyz2))
      (SETQ z (RTOS z 2 5))
      (SETQ Y (CADR xyz2))
      (SETQ Y (RTOS Y 2 5))
      (SETQ X (CAR xyz2)) 
      (SETQ X (RTOS X 2 5))
      (command "INSERT" (STRCAT RUTA "BLOCKS\\PUN2") (STRCAT X "," Y) ".1" ".1" "" "" "" "" "" "" "")
      (SETQ BLOCK (ENTLAST))
      (SETQ BLOCK (ENTNEXT BLOCK))
      (COMMAND "ATTEDIT" "" "" "" "" BLOCK "V" "R" "INTERPOLADO" "")
      (SETQ BLOCK (ENTNEXT BLOCK))
      (COMMAND "ATTEDIT" "" "" "" "" BLOCK "V" "R" Z "")
      (SETQ BLOCK (ENTNEXT BLOCK))
      (COMMAND "ATTEDIT" "" "" "" "" BLOCK "V" "R" "1" "")
      (SETQ T1 (1+ T1))
      (setq e (ssname gpoin T1))
    )
  (COMMAND "ERASE" GPOIN "")
  (SETVAR "OSMODE" OPCIONESOS)
)

(DEFUN C:INTER ()
    (COMMAND "UNDO" "M")
    (C:LIBRERIA "busca block en base de datos")
    (C:LIBRERIA "BUSCA VALOR DE ATRIBUTO")
    (SETQ OPCIONESOS (GETVAR "OSMODE"))
    (command "osnap" "none")
    (SETQ VALIDA (SBLBD "X"))
    (IF (/= "S" VALIDA) (SETQ VALIDA (SBLBD "PUN2")))
    (If (/= VALIDA "S") 
      (PROGN 
       (COMMAND "INSERT" (STRCAT RUTA "BLOCKS\\PUN2.DWG") "0,0" "" "" "" "")
       (COMMAND "ERASE" (ENTLAST) "")
      )
    )
    (setq block (car (entsel "primer block : ")))
    (setq block2 (car (entsel "segundo block : ")))
    (setq xyz (cdr (assoc 10 (entget block))))
    (setq xyz2 (cdr (assoc 10 (entget block2))))
    (SETQ DISTA (DISTANCE XYZ XYZ2))
    (SETQ NDIV (1+ (FIX DISTA)))
    (SETQ Y (CADR xyz))
    (SETQ Y (RTOS Y 2 5))
    (SETQ X (CAR xyz))
    (SETQ X (RTOS X 2 5))
    (SETQ Y2 (CADR xyz2))
    (SETQ Y2 (RTOS Y2 2 5))
    (SETQ X2 (CAR xyz2))
    (SETQ X2 (RTOS X2 2 5))
    (setq elev1 (busatr block "ELEV"))
    (setq elev2 (busatr block2 "ELEV"))
    (command "line" ".xy" (strcat x "," y) elev1 ".xy" (strcat x2 "," y2) elev2 "")
    (SETQ LIN (ENTLAST))
    (SETVAR "OSMODE" 512)
    (SETQ PTOF (GETPOINT "\n Dame el punto final para colocar el block"))
    (command "osnap" "none")
    (SETQ z (CADdR ptof))
    (SETQ z (RTOS z 2 3))
    (SETQ Y (CADR ptof))
    (SETQ Y (RTOS Y 2 5))
    (SETQ X (CAR ptof))
    (SETQ X (RTOS X 2 5))
    (command "insert" (STRCAT RUTA "BLOCKS\\pun2") (strcat x "," y) ".1" ".1" "" "" "" "" "" "" "")
    (SETQ BLOCK (ENTLAST))
    (SETQ BLOCK (ENTNEXT BLOCK))
    (COMMAND "ATTEDIT" "" "" "" "" BLOCK "V" "R" "INTERPOLADO" "")
    (SETQ BLOCK (ENTNEXT BLOCK))
    (COMMAND "ATTEDIT" "" "" "" "" BLOCK "V" "R" z "")
    (SETQ BLOCK (ENTNEXT BLOCK))
    (COMMAND "ATTEDIT" "" "" "" "" BLOCK "V" "R" "1" "")
    (command "erase" lin "")
    (SETVAR "OSMODE" OPCIONESOS)
)


(DEFUN C:mid ()
    (COMMAND "UNDO" "M")
    (C:LIBRERIA "busca block en base de datos")
    (C:LIBRERIA "BUSCA VALOR DE ATRIBUTO")
    (SETQ OPCIONESOS (GETVAR "OSMODE"))
    (command "osnap" "none")
    (SETQ VALIDA (SBLBD "X"))
    (IF (/= "S" VALIDA) (SETQ VALIDA (SBLBD "x")))
    (If (/= VALIDA "S") 
      (PROGN 
       (COMMAND "INSERT" (STRCAT RUTA "BLOCKS\\X.DWG") "0,0" "" "" "" "")
       (COMMAND "ERASE" (ENTLAST) "")
      )
    )
    (setq block (car (entsel "primer block : ")))
    (setq block2 (car (entsel "segundo block : ")))
    (setq xyz (cdr (assoc 10 (entget block))))
    (setq xyz2 (cdr (assoc 10 (entget block2))))
    (SETQ DISTA (DISTANCE XYZ XYZ2))
    (SETQ NDIV (1+ (FIX (/ DISTA 2))))
    (SETQ Y1 (CADR xyz))
    (SETQ X1 (CAR xyz))
    (SETQ Y2 (CADR xyz2))
    (SETQ X2 (CAR xyz2))
    (setq elev1 (busatr block "ELEV"))
    (setq elev2 (busatr block2 "ELEV"))
  (setq xd (- x1 x2))
  (if (> 0 xd)
    (setq xd (* xd -1))
  )
  (setq xd (/ xd 2))

  (setq yd (- y1 y2))
  (if (> 0 yd)
    (setq yd (* yd -1))
  )
  (setq yd (/ yd 2))
  (if (> x1 x2)
    (setq xd (+ xd x2))
    (setq xd (+ xd x1))
  )
  (if (> y1 y2)
    (setq yd (+ yd y2))
    (setq yd (+ yd y1))
  )
  (if (> (atof elev1) (atof elev1))
    (progn
      (setq zprom (/ (- (atof elev1) (atof elev2)) 2))
      (setq zfinal (+ (atof elev2) zprom))
    )
    (progn
      (setq zprom (/ (- (atof elev2) (atof elev1)) 2))
      (setq zfinal (+ (atof elev1) zprom))
    )
  )
  (setq punmid (list xd yd))
      (command "INSERT" (STRCAT RUTA "BLOCKS\\PUN2") punmid ".1" ".1" "" "" "" "" "" "" "" "" "")
      (SETQ BLOCK (ENTLAST))
      (SETQ BLOCK (ENTNEXT BLOCK))
      (COMMAND "ATTEDIT" "" "" "" "" BLOCK "V" "R" "INTERPOLADO" "")
      (SETQ BLOCK (ENTNEXT BLOCK))
      (COMMAND "ATTEDIT" "" "" "" "" BLOCK "V" "R" (rtos Zfinal 2 3) "")
      (SETQ BLOCK (ENTNEXT BLOCK))
      (COMMAND "ATTEDIT" "" "" "" "" BLOCK "V" "R" "1" "")
)

(DEFUN C:mid2 ()
    (COMMAND "UNDO" "M")
    (C:LIBRERIA "busca block en base de datos")
    (C:LIBRERIA "BUSCA VALOR DE ATRIBUTO")
    (SETQ OPCIONESOS (GETVAR "OSMODE"))
    (command "osnap" "none")
    (SETQ VALIDA (SBLBD "X"))
    (IF (/= "S" VALIDA) (SETQ VALIDA (SBLBD "x")))
    (If (/= VALIDA "S") 
      (PROGN 
       (COMMAND "INSERT" (STRCAT RUTA "BLOCKS\\X.DWG") "0,0" "" "" "" "")
       (COMMAND "ERASE" (ENTLAST) "")
      )
    )
    (setq block (car (entsel "primer block : ")))
    (setq block2 (car (entsel "segundo block : ")))
    (setq xyz (cdr (assoc 10 (entget block))))
    (setq xyz2 (cdr (assoc 10 (entget block2))))
    (SETQ DISTA (DISTANCE XYZ XYZ2))
    (SETQ NDIV (1+ (FIX (/ DISTA 2))))
    (SETQ Y1 (CADR xyz))
    (SETQ X1 (CAR xyz))
    (SETQ Y2 (CADR xyz2))
    (SETQ X2 (CAR xyz2))
    (setq elev1 (busatr block "ELEV"))
    (setq elev2 (busatr block2 "ELEV"))
  (setq xd (- x1 x2))
  (if (> 0 xd)
    (setq xd (* xd -1))
  )
  (setq xd (/ xd 2))

  (setq yd (- y1 y2))
  (if (> 0 yd)
    (setq yd (* yd -1))
  )
  (setq yd (/ yd 2))
  (if (> x1 x2)
    (setq xd (+ xd x2))
    (setq xd (+ xd x1))
  )
  (if (> y1 y2)
    (setq yd (+ yd y2))
    (setq yd (+ yd y1))
  )
  (if (> (atof elev1) (atof elev1))
    (progn
      (setq zprom (/ (- (atof elev1) (atof elev2)) 2))
      (setq zfinal (+ (atof elev2) zprom))
    )
    (progn
      (setq zprom (/ (- (atof elev2) (atof elev1)) 2))
      (setq zfinal (+ (atof elev1) zprom))
    )
  )
  (setq distancia (/ (distance xyz xyz2) 2))
  (setq zfinal (+ zfinal (* distancia 0.02)))
  (setq punmid (list xd yd))
      (command "INSERT" (STRCAT RUTA "BLOCKS\\PUN2") punmid ".1" ".1" "" "" "" "" "" "" "" "" "")
      (SETQ BLOCK (ENTLAST))
      (SETQ BLOCK (ENTNEXT BLOCK))
      (COMMAND "ATTEDIT" "" "" "" "" BLOCK "V" "R" "INTERPOLADO" "")
      (SETQ BLOCK (ENTNEXT BLOCK))
      (COMMAND "ATTEDIT" "" "" "" "" BLOCK "V" "R" (rtos Zfinal 2 3) "")
      (SETQ BLOCK (ENTNEXT BLOCK))
      (COMMAND "ATTEDIT" "" "" "" "" BLOCK "V" "R" "1" "")
)
