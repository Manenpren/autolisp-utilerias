(Defun c:ABL ()
    (setq PUNTO (getpoint " DAME EL CENTRO DEL AREA : "))
    (setq block (car (entsel " texto destino : ")))
    (setq xy (cdr (assoc 10 (entget block))))
    (setq x (car xy))
    (setq prov (cadr xy))
    (setq y (- prov .05))
    (setq sel (strcat "0," Y))
    (COMMAND "BPOLY" PUNTO "")
    (setq LIN (entlast))
    (command "AREA" "OB" LIN "")
    (SETQ AREA (RTOS (GETVAR "AREA") 2 3))
    (COMMAND "attedit" "" "nomar" "area" "" xy sel "" "v" "r" AREA)
    (command "erase" lin "")
)
