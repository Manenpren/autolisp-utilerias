(defun C:ARSEC ()
    (C:LIBRERIA "busca block en base de datos")
    (C:LIBRERIA "ZOOM ULTIMO OBJETO INSERTADO")
    (C:LIBRERIA "VERTICES DE UNA LWPOLYLINE")
    (COMMAND "UNDO" "M")
    (COMMAND "VIEW" "S" "C")
    (SETQ OPCIONESOS (GETVAR "OSMODE"))
    (SETVAR "OSMODE" 16384)
    (SETQ ACORTE 0)
    (SETQ ATERRAP 0)
    (SETQ GPOAREAS (SSADD))
  (setq BLOCK (CAR (ENTSEL "SELECCIONA BLOCK a procesar")))
  (setq NOMBLO (cdr (assoc 2 (entget block))))
  (setq nb2 nomblo)
  (COMMAND "INSERT" NOMBLO "0,0" "" "" "")
  (SETQ X (ENTLAST))
  (ZBLOCK)
    (command "layer" "s" "tn" "OFf" "RETICULA" "OFf" "PROYECTO" "OFf" "LINEAS" "OFf" "terreno N" "")
;    (command "change" poltn "" "p" "la" "reticula")
    (setq xyz (vertice polTN 1))
    (SETQ CONT1 2)
    (SETQ XYZ2 1)
;    (SETQ LOG1 0)
    (SETQ INTERSEC 0)
    (setq gpointt (ssadd))
    (while xyz2
      (setq xyz2 (vertice polTN CONT1))
      (SETQ CONT1 (1+ CONT1))
      (IF XYZ2
       (PROGN
        (SETQ PX1 (CAR XYZ))
        (SETQ PY1 (CADR XYZ))
        (SETQ PX2 (CAR XYZ2))
        (SETQ PY2 (CADR XYZ2))
        (if (> px1 px2) (setq sumx 0.0001) (setq sumx -0.0001))
        (if (> py1 py2) (setq sumy 0.0001) (setq sumy -0.0001))
        (SETQ GPOINT (SSGET "CP" (LIST (suma XYZ sumx sumy) (suma XYZ sumx (* sumy -1)) (suma XYZ2 (* sumx -1) (* sumy -1)) (suma XYZ2 (* sumx -1) sumy))))
        (IF (> (SSLENGTH GPOINT) 1)
          (PROGN
            (SETQ E (SSNAME GPOINT 0))
            (SETQ CONT2 1)
            (WHILE E
               (IF (AND (= (cdr (assoc 0 (ENTGET E))) "LINE") (= (STRCASE (cdr (assoc 8 (ENTGET E)))) "PR"))
                 (PROGN
                   (SETQ PTOPR1 (cdr (assoc 10 (ENTGET E))))
                   (SETQ PTOPR2 (cdr (assoc 11 (ENTGET E))))
                   (IF (/= PX1 PX2)
                     (SETQ M1 (/ (- PY2 PY1) (- PX2 PX1)))
                   )
                   (SETQ P2X1 (CAR PTOPR1))
                   (SETQ P2Y1 (CADR PTOPR1))
                   (SETQ P2X2 (CAR PTOPR2))
                   (SETQ P2Y2 (CADR PTOPR2))
                   (IF (/= P2X1 P2X2)
                     (SETQ M2 (/ (- P2Y2 P2Y1) (- P2X2 P2X1)))
                   )
                   (IF (AND (/= P2X1 P2X2) (/= PX1 PX2))
                     (PROGN
                       (SETQ INTX (/ (+ (- P2Y1 (* P2X1 M2) PY1) (* PX1 M1)) (- M1 M2)))
                       (SETQ INTY (- (+ PY1 (* INTX M1)) (* PX1 M1)))
                     );PROGN
                   );IF
                   (IF (AND (= P2X1 P2X2) (/= PX1 PX2))
                     (PROGN
                       (SETQ INTX P2X1)
                       (SETQ INTY (- (+ PY1 (* INTX M1)) (* PX1 M1)))
                     )
                   )
                   (IF (AND (/= P2X1 P2X2) (= PX1 PX2))
                     (PROGN
                       (SETQ INTX PX1)
                       (SETQ INTY (- (+ P2Y1 (* INTX M2)) (* P2X1 M2)))
                     )
                   )
                   (COMMAND "point" (STRCAT (RTOS INTX) "," (RTOS INTY)))
                   (ssadd (entlast) gpointt)
                 )
               )
               (SETQ E (SSNAME GPOINT CONT2))
               (SETQ CONT2 (1+ CONT2))
            )                             ;WHILE
;            (COMMAND "CIRCLE" XYZ XYZ2)
          )                               ;PROGN
        )                                 ;IF
        (SETQ XYZ XYZ2)
       );PROGN
      );IF
    )
    (SETQ E (SSNAME GPOINTt 0))
    (SETQ xyz (cdr (assoc 10 (ENTGET E))))
    (SETQ PXint (CAR xyz))
    (SETQ PYint (CADR xyz))
    (SETQ CONT1 1)
    (SETQ GPOINT (SSGET "CP" (LIST (suma XYZ 0.0001 0.0001) (suma XYZ -0.0001 0.0001) (suma XYZ -0.0001 -0.0001) (suma XYZ 0.0001 -0.0001)) '((0 . "LINE"))))
    (SETQ E2 (SSNAME GPOINT 0))
    (setq contx 1)
    (while e2
      (if (and (= (cdr (assoc 0 (ENTGET E2))) "LINE") (= (strcase (cdr (assoc 8 (ENTGET E2)))) "PR"))
         (PROGN
            (SETQ pxyz (cdr (assoc 10 (ENTGET E2))))
            (SETQ pxyz2 (cdr (assoc 11 (ENTGET E2))))
            (SETQ PX1 (CAR Pxyz))
            (SETQ PY1 (CADR Pxyz))
            (SETQ PX2 (CAR Pxyz2))
            (SETQ PY2 (CADR Pxyz2))
            (SETQ GPOprov (SSGET "CP" (LIST (suma PXYZ 0.0001 0.0001) (suma PXYZ -0.0001 0.0001) (suma PXYZ -0.0001 -0.0001) (suma PXYZ 0.0001 -0.0001)) '((0 . "LINE"))))
            (SETQ GPOprov2 (SSGET "CP" (LIST (suma pXYZ2 0.0001 0.0001) (suma pXYZ2 -0.0001 0.0001) (suma pXYZ2 -0.0001 -0.0001) (suma pXYZ2 0.0001 -0.0001)) '((0 . "LINE"))))
            (if (and (> (SSLENGTH GPOprov) 1) (< py1 pyint) (/= PX1 PXINT))
              (PROGN
                (setq orden "corte")
                (SETQ PREF PXYZ)
                (SETQ PREFX PX1)
                (SETQ PREFY PY1)
              )
            )
            (if (and (> (SSLENGTH GPOprov2) 1) (< py2 pyint) (/= PX2 PXINT))
              (PROGN
                (setq orden "corte")
                (SETQ PREF PXYZ2)
                (SETQ PREFX PX2)
                (SETQ PREFY PY2)
              )
            )
            (if (and (> (SSLENGTH GPOprov) 1) (> py1 pyint) (/= PX1 PXINT))
              (PROGN
                (setq orden "terrap")
                (SETQ PREF PXYZ)
                (SETQ PREFX PX1)
                (SETQ PREFY PY1)
              )
            )
            (if (and (> (SSLENGTH GPOprov2) 1) (> py2 pyint) (/= PX2 PXINT))
              (PROGN
                (setq orden "terrap")
                (SETQ PREF PXYZ2)
                (SETQ PREFX PX2)
                (SETQ PREFY PY2)
              )
            )
         )
      )
      (SETQ E2 (SSNAME GPOINT contx))
      (setq contx (1+ contx))
    )                          ;while
    (SETQ E (SSNAME GPOINTt 1))
    (SETQ Pxyz2 (cdr (assoc 10 (ENTGET E))))
    (SETQ PXint2 (CAR Pxyz2))
    (SETQ PYint2 (CADR Pxyz2))
    (setq cont1 2)
    (while e
      (setq xd (- PREFX pxint))
      (if (> 0 xd)
        (setq xd (* xd -1))
      )
      (setq xd (/ xd 2))
      (setq yd (- PREFY pyint))
      (if (> 0 yd)
        (setq yd (* yd -1))
      )
      (setq yd (/ yd 2))
      (if (> pxint PREFX)
        (setq xd (+ xd pREFX))
        (setq xd (+ xd pxint))
      )
      (if (> pyint pREFY)
        (setq yd (+ yd pREFY))
        (setq yd (+ yd pyint))
      )
      (SETQ V (- pxint2 pxint))
      (if (> 0 V)
        (setq V (* V -1))
      )
      (SETQ V2 (- pYint2 pYint))
      (if (> 0 V2)
        (setq V2 (* V2 -1))
      )
      (setq xd2 (- PXINT2 pxint))                        ;MITAD DE INTERSECCIONES
      (if (> 0 xd2)
        (setq xd2 (* xd2 -1))
      )
      (setq xd2 (/ xd2 2))
      (setq yd2 (- PYINT2 pyint))
      (if (> 0 yd2)
        (setq yd2 (* yd2 -1))
      )
      (setq yd2 (/ yd2 2))
      (if (> pxint PXINT2)
        (setq xd2 (+ xd2 pXINT2))
        (setq xd2 (+ xd2 pxint))
      )
      (if (> pyint pYINT2)
        (setq yd2 (+ yd2 pYINT2))
        (setq yd2 (+ yd2 pyint))
      )
      (SETQ DI1 (DISTANCE XYZ PXYZ2))
      (SETQ DI2 (DISTANCE PREF XYZ))
      (IF (> DI1 DI2)
        (COMMAND "ZOOM" "w" xyz pxyz2)
        (COMMAND "ZOOM" "C" (STRCAT (RTOS XD2) "," (RTOS YD2)) V)
      )
      (SETQ N ORDEN)
      (if (= orden "corte") 
        (setq yprv (+ YD (* V2 0.03)))
      )
      (if (= orden "terrap") 
        (setq yprv (- YD (* V2 0.03)))
      )
      (if (= orden "terrap") 
        (setq orden "corte")
        (setq orden "terrap")
      )
      (setq xyzprv (strcat (rtos xd) "," (rtos yprv)))
      (COMMAND "-BOUNDARY" XYZprv "")
      (COMMAND "AREA" "E" "L")
      (SETQ AP (RTOS (GETVAR "AREA") 2 3))
;      (command "circle" xyzprv "0.3")
      (COMMAND "INSERT" (strcat ruta "blocks\\NOMAR") XYZprv "" "" "" "" "")
      (ssadd (entlast) gpoAREAS)
      (SETQ EAREAS (ENTLAST))
      (setq bl (entnext EAREAS))
      (COMMAND "attedit" "" "" "" "" bl "V" "R" N "")
      (setq bl (entnext BL))
      (COMMAND "attedit" "" "" "" "" bl "V" "R" AP "")
      (IF (= N "corte") (SETQ ACORTE (+ ACORTE (ATOF AP))))
      (IF (= N "terrap") (SETQ ATERRAP (+ ATERRAP (ATOF AP))))
      (SETQ E (SSNAME GPOINTt cont1))
      (setq cont1 (1+ cont1))
      (setq xyz Pxyz2)
      (setq pxint pxint2)
      (setq pyint pyint2)
      (if e
        (progn
          (SETQ Pxyz2 (cdr (assoc 10 (ENTGET E))))
;          (command "circle" Pxyz2 "0.1")
          (SETQ PXint2 (CAR Pxyz2))
          (SETQ PYint2 (CADR Pxyz2))
        )
      )
      (command "zoom" "p")
      (SETQ GPOprov (SSGET "CP" (LIST (suma XYZ 0.0001 0.0001) (suma XYZ -0.0001 0.0001) (suma XYZ -0.0001 -0.0001) (suma XYZ 0.0001 -0.0001)) '((0 . "LINE"))))
      (SETQ E3 (SSNAME GPOPROV 0))
      (SETQ pxyzX (cdr (assoc 10 (ENTGET E3))))
      (SETQ pxyz2X (cdr (assoc 11 (ENTGET E3))))
      (SETQ PX1X (CAR PxyzX))
      (SETQ PY1X (CADR PxyzX))
      (SETQ PX2X (CAR Pxyz2X))
      (SETQ PY2X (CADR Pxyz2X))
      (IF (> PXINT2 PXINT)
        (progn
          (IF (< PXINT PX1X)
            (PROGN
              (SETQ PREF PXYZX)
              (SETQ PREFX PX1X)
              (SETQ PREFY PY1X)
            )
          )
          (IF (< PXINT PX2X)
            (PROGN
              (SETQ PREF PXYZ2X)
              (SETQ PREFX PX2X)
              (SETQ PREFY PY2X)
            )
          )
          (IF (= (RTOS PX2x 2 4) (RTOS PX1X 2 4))
            (PROGN
              (IF (= ORDEN "corte")
                (PROGN
                  (IF (> PyINT Py1X)
                    (progn
                      (SETQ PREF PXYZX)
                      (SETQ PREFX PX1X)
                      (SETQ PREFY PY1X)
                    )
                  )
                  (IF (< PyINT Py1X)
                    (progn
                      (SETQ PREF PXYZ2X)
                      (SETQ PREFX PX1X)
                      (SETQ PREFY PY2X)
                    )
                  )
                );PROGN
              )
              (IF (= ORDEN "terrap")
                (PROGN
                  (IF (> PyINT Py1X)
                    (progn
                      (SETQ PREF PXYZ2X)
                      (SETQ PREFX PX1X)
                      (SETQ PREFY PY2X)
                    )
                  )
                  (IF (< PyINT Py1X)
                    (progn
                      (SETQ PREF PXYZX)
                      (SETQ PREFX PX1X)
                      (SETQ PREFY PY1X)
                    )
                  )
                );PROGN
              )
              (setq prefx (- prefx (* V 0.03)))
            )
          );IF =
        );progn
      );if
      (IF (< PXINT2 PXINT)
        (progn
          (IF (< PXINT PX1X)
            (PROGN
              (SETQ PREF PXYZ2X)
              (SETQ PREFX PX2X)
              (SETQ PREFY PY2X)
            )
          )
          (IF (< PXINT PX2X)
            (PROGN
              (SETQ PREF PXYZX)
              (SETQ PREFX PX1X)
              (SETQ PREFY PY1X)
            )
          )
          (IF (= (RTOS PX2x 2 4) (RTOS PX1X 2 4))
            (PROGN
              (IF (= ORDEN "corte")
                (PROGN
                  (IF (> PyINT Py1X)
                    (progn
                      (SETQ PREF PXYZX)
                      (SETQ PREFX PX1X)
                      (SETQ PREFY PY1X)
                    )
                  )
                  (IF (< PyINT Py1X)
                    (progn
                      (SETQ PREF PXYZ2X)
                      (SETQ PREFX PX1X)
                      (SETQ PREFY PY2X)
                    )
                  )
                )
              )
              (IF (= ORDEN "terrap")
                (PROGN
                  (IF (> PyINT Py1X)
                    (progn
                      (SETQ PREFX PX1X)
                      (SETQ PREF PXYZ2X)
                      (SETQ PREFY PY2X)
                    )
                  )
                  (IF (< PyINT Py1X)
                    (progn
                      (SETQ PREF PXYZX)
                      (SETQ PREFX PX1X)
                      (SETQ PREFY PY1X)
                    )
                  )
                );PROGN
              )
              (setq prefx (- prefx (* V 0.03)))
            )
          );if =
        );progn
      );if
;      (command "circle" (strcat (rtos prefx) "," (rtos prefy)) "0.1")
    );DO
      (COMMAND "INSERT" (strcat ruta "blocks\\NOMAR") XYZprv "" "" "" "" "")
      (SETQ EAREAS (ENTLAST))
      (setq bl (entnext EAREAS))
      (COMMAND "attedit" "" "" "" "" bl "V" "R" "CORTE" "")
      (setq bl (entnext BL))
      (COMMAND "attedit" "" "" "" "" bl "V" "R" (RTOS ACORTE 2 3) "")
      (COMMAND "INSERT" (strcat ruta "blocks\\NOMAR") XYZprv "" "" "" "" "")
      (SETQ EAREAS (ENTLAST))
      (setq bl (entnext EAREAS))
      (COMMAND "attedit" "" "" "" "" bl "V" "R" "TERRAP" "")
      (setq bl (entnext BL))
      (COMMAND "attedit" "" "" "" "" bl "V" "R" (RTOS ATERRAP 2 3) "")
      (COMMAND "ERASE" GPOAREAS "")
    (command "layer" "ON" "RETICULA" "ON" "PROYECTO" "")
    (SETVAR "OSMODE" OPCIONESOS)
)

(DEFUN SUMA (P VX VY)
  (SETQ X (CAR P))
  (SETQ Y (CAR (CDR P)))
  (LIST (+ X VX) (+ Y VY) (LAST P))
)
