(DEFUN SUMA (P VX VY)
  (SETQ X (CAR P))
  (SETQ Y (CAR (CDR P)))
  (LIST (+ X VX) (+ Y VY) (LAST P))
)

(defun equis ()
  (if (< xmayor (atof dat))
    (setq xmayor (atof dat))
  )
  (if (> xmenor (atof dat))
    (setq xmenor (atof dat))
  )
)

(defun ye ()
  (if (< ymayor (atof dat))
    (setq ymayor (atof dat))
  )
  (if (> ymenor (atof dat))
    (setq ymenor (atof dat))
  )
)


(DEFUN COLUMNAS ()
  (SETQ CA (SUBSTR LIN 1 1))
  (SETQ C 0) (SETQ X 1)
  (setq xmayor 0) (setq xmenor 0) (setq ymayor 0) (setq ymenor 0)
  (WHILE (/= C 3)
    (SETQ C (+ C 1))
    (SETQ DAT "")
    (WHILE (/= CA ",")
      (SETQ X (+ X 1))
      (SETQ DAT (STRCAT DAT CA))
      (SETQ CA (SUBSTR LIN X 1))
    )
    (SETQ CA "")
    (if (= c 1)
      (equis)
    )
    (if (= c 2)
      (ye)
    )
  )
)


(DEFUN LEE ()
  (SETQ LIN (READ-LINE arch))
  (SETQ L 1)
  (LEEINI)
  (WHILE (AND LIN (<= L FIN))
    (COLUMNAS)
    (SETQ L (+ L 1))
    (SETQ LIN (READ-LINE arch))
  )
  (SETQ L (- L 1))
)

(defun camatr ()
  (setq atrib (cdr (assoc 2 (entget ent))))
  (setq nocol (cdr (assoc atrib datos)))
  (setq valor (cdr (assoc nocol atributos)))
  (entmod (subst (cons 1 valor)
                 (assoc 1 (entget ent))
                 (entget ent)
          )
  )
)

(defun cambiaatr ()
  (setq ent (entlast))
  (while ent
    (if (= "ATTRIB" (cdr (assoc 0 (entget ent))))
      (camatr)
    )
    (setq ent (entnext ent))
  )
)

(DEFUN COLUMNAS2 ()
  (SETQ CA (SUBSTR LIN 1 1))
  (SETQ C 0) (SETQ X 1)
  (SETQ ATRIBUTOS NIL)
  (WHILE (/= C (+ noatri 3))
    (SETQ C (+ C 1))
    (SETQ DAT "")
    (SETQ SALIR "N")
    (WHILE SALIR
      (SETQ X (+ X 1))
      (SETQ DAT (STRCAT DAT CA))
      (SETQ CA (SUBSTR LIN X 1))
      (IF (= CA ",")
        (SETQ SALIR nil)
      )
      (IF (= CA "")
        (SETQ SALIR nil)
      )
    )
    (SETQ CA "")
    (setq atributo (cons c dat))
    (setq atributos (append atributos (list atributo)))
  )
  (IF (= "3" TRI)
    (COMMAND "COPY" UL "" (LIST ex ey) (LIST (ATOF (CDR (ASSOC 1 ATRIBUTOS)))
                                             (ATOF (CDR (ASSOC 2 ATRIBUTOS)))
                                             (ATOF (CDR (ASSOC 3 ATRIBUTOS)))))
    (COMMAND "COPY" UL "" (LIST ex ey) (LIST (ATOF (CDR (ASSOC 1 ATRIBUTOS)))
                                             (ATOF (CDR (ASSOC 2 ATRIBUTOS)))))
  )
  (cambiaatr)
)

(DEFUN LEEINI ()
  (WHILE (/= L INI)
    (SETQ L (+ L 1))
    (SETQ LIN (READ-LINE arch))
  )
)

(DEFUN LEE2 ()
  (SETQ LIN (READ-LINE arch))
  (SETQ L 1) (setq atributos nil)
  (LEEINI)
  (WHILE (AND LIN (<= L FIN))
    (COLUMNAS2)
    (SETQ L (+ L 1))
    (SETQ LIN (READ-LINE arch))
  )
  (SETQ L (- L 1))
)

(defun proatrib ()
  (setq noatri (+ noatri 1))
  (setq nomatr (cdr (assoc 2 (entget e))))
  (print nomatr)
  (setq columna (getint " No. de columna para este atributo: "))
  (setq dato (cons nomatr columna))
  (setq datos (append datos (list dato)))
)

(defun abloque ()
  (setq e (cdr (assoc -2 lisblo)))
  (setq noatri 0) (setq datos nil)
  (while e
    (if (= "ATTDEF" (cdr (assoc 0 (entget e))))
      (PROATRIB)
    )
    (setq e (entnext e))
  )
  (print noatri)
)

(defun continua ()
  (setq nomblo (getstring "\n Nombre del bloque: "))
  (setq ex 1.13)
  (setq ey 1.13) 
  (setq tt (getreal "\n Tamaño minimo de texto a manejar: "))
  (command "INSERT" nomblo (list ex ey) tt "" ""
   "" "" "" "" "" "" "" "" "" "" "" "" "" "" "" "" "" "" "" "" "" "" "" ""
   "" "" "" "" "" "" "" "" "" "" "" "" "" "" "" "" "" "" "" "" "" "" "" "")
  (SETQ UL (ENTLAST))
  (setq nomarch (getstring "\n Nombre del archivo de datos: "))
  (setq ini (getint "\n Renglon donde se inica la lectura: "))
  (setq fin (getint "\n Renglon donde termina la lectura: "))
  (setq tri (getstring "\n Teclear 3 para tridimensional y 2 para bidimencional: "))
  (setq lisblo (tblsearch "block" nomblo))
  (ABLOQUE)
  (setq arch (OPEN NOMARCH "r"))
  (if arch
    (LEE)
    (print "\n Archivo no encontrado ")
  )
  (close arch)
  (command "ZOOM" "w" (list xmayor ymayor) (list xmenor ymenor))
  (setq arch (OPEN NOMARCH "r"))
  (if arch
    (LEE2)
  )
  (close arch)
  (entdel ul)
  (command "ZOOM" "E")
)

(defun c:insatr ()
  (continua)
)
