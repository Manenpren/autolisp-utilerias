(defun c:IB ()
    (setq texto (car (entsel "Selecciona el texto: ")))
    (setq NOMBRE (cdr (assoc 1 (entget TEXTO))))
    (SETQ LNG (STRLEN NOMBRE))
    (SETQ NOMBLO "")
    (SETQ CONT 0)
    (REPEAT LNG
        (SETQ CONT (1+ CONT))
        (setq CARACTER (substr NOMBRE CONT 1))
        (IF (= CARACTER "+") (SETQ CARACTER "-"))
        (setq nomblo (STRCAT NOMBLO CARACTER))
    )
    (command "insert" nomblo)
)
