(defun C:pP ()
    (SETQ NUM (GETINT " NUMERO DE TEXTOS: " ))
    (SETQ CALLE (GETSTRING " CALLE: " ))
    (SETQ COTA 0)
    (REPEAT NUM
        (setq texto (car (entsel "Selecciona el texto: ")))
        (setq NOMBRE (cdr (assoc 1 (entget TEXTO))))
        (IF (>= COTA 100)
            (SETQ PROV "0+")    
            (SETQ PROV "0+0")    
        )
        (IF (= COTA 0)
            (SETQ PROV "0+00")    
        )
        (setq nomblo (strcat PROV (ITOA COTA) "-" CALLE))
        (COMMAND "CHANGE" texto "" "" "" "" "" "" NOMBLO)
        (SETQ COTA (+ COTA 20))
    )
)
