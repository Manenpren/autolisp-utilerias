(DEFUN SUMA (P VX VY)
  (SETQ X (CAR P))
  (SETQ Y (CAR (CDR P)))
  (LIST (+ X VX) (+ Y VY) (LAST P))
)

(DEFUN COLUMNAS ()
  (SETQ CA (SUBSTR LIN 1 1))
  (SETQ C 0) (SETQ X 1)
  (WHILE (/= CA "")
    (SETQ C (+ C 1))
    (SETQ DATO "")
    (WHILE (AND (/= CA ",") (/= CA ""))
      (SETQ X (+ X 1))
      (SETQ DATO (STRCAT DATO CA))
      (SETQ CA (SUBSTR LIN X 1))
    )
    (SETQ DATO (CONS (STRCAT (ITOA L) "-" (ITOA C)) DATO))
    (SETQ DATOSlp (APPEND DATOSlp (LIST DATO)))
    (SETQ CA (SUBSTR LIN (+ X 1) 1))
    (SETQ X (+ X 1))
  )
)

(DEFUN ANALIZA ()
  (SETQ NC 0) (SETQ LONTOT 0)
  (SETQ LONCOLS (LIST))
  (WHILE (/= NC C)
    (SETQ NC (+ NC 1))
    (SETQ NL 0) (SETQ LONG 0)
    (WHILE (/= NL L)
      (SETQ NL (+ NL 1))
      (SETQ CLAVE (STRCAT (ITOA NL) "-" (ITOA NC)))
      (IF (> (STRLEN (CDR (ASSOC CLAVE DATOSlp))) LONG)
        (SETQ LONG (STRLEN (CDR (ASSOC CLAVE DATOSlp))))
      )
    )
    (PRINC "\n")
;    (SETQ M1 (STRCAT " LONGITUD MINIMA COLUMNA No. " (ITOA NC)))
;    (SETQ M2 (STRCAT M1 "  " (ITOA (+ LONG 1)) " CARACTERES "))
;    (PRINC M2)
;    (SETQ LONCOL (GETINT "\n LONGITUD DE COLUMNA:  "))
    (SETQ LONCOLS (APPEND LONCOLS (LIST (+ long 1))))
    (SETQ LONTOT (+ LONTOT (+ long 1)))
  )
  (SETQ TAM 1)
)

(DEFUN LEELP ()
  (SETQ LIN (READ-LINE TBL))
  (SETQ L 1)
  (SETQ DATOSlp (LIST))
  (WHILE LIN 
    (COLUMNAS)
    (SETQ L (+ L 1))
    (SETQ LIN (READ-LINE TBL))
  )
  (SETQ L (- L 1))
  (ANALIZA)
  (CLOSE TBL)
)

(DEFUN LINEAS ()
  (setq gpolintopf (ssadd))
  (SETQ LONGITUD (* LONTOT TAM))
  (SETQ EII (GETPOINT "\n ESQUINA INFERIOR IZQ. DE TABLA "))
  (SETQ TAM2 (POLAR EII 1.5708 (* TAM 2 L)))
  (SETQ NC2 -1) (SETQ DIST 0)
  (WHILE (/= NC2 (- C 1))
    (SETQ NC2 (+ NC2 1))
    (SETQ DIST (+ DIST (* (NTH NC2 LONCOLS) TAM)))
  )
  (COMMAND "ZOOM" "W"  (SUMA TAM2 -2 2) (SUMA EII DIST -2))
  (COMMAND "LINE" EII (POLAR EII 0 LONGITUD) "")
  (SETQ GPOLINTOPF (SSADD (SSNAME (SSGET "L") 0) GPOLINTOPF))
  (REPEAT L
    (COMMAND "ARRAY" "LAST" "" "R" 2 1 (* TAM 2))
    (SETQ GPOLINTOPF (SSADD (SSNAME (SSGET "L") 0) GPOLINTOPF))
  )
  (COMMAND "LINE" EII (POLAR EII 1.5708 (* TAM 2 L)) "")
  (SETQ GPOLINTOPF (SSADD (SSNAME (SSGET "L") 0) GPOLINTOPF))
  (SETQ NC2 -1) (SETQ DIST 0)
  (WHILE (/= NC2 (- C 1))
    (SETQ NC2 (+ NC2 1))
    (SETQ DIST (+ DIST (* (NTH NC2 LONCOLS) TAM)))
    (COMMAND "LINE" (SUMA EII DIST 0) (SUMA (POLAR EII 1.5708 (* TAM 2 L)) DIST 0) "")
    (SETQ GPOLINTOPF (SSADD (ENTLAST) GPOLINTOPF))
  )
)

(DEFUN COLOCA ()
  (SETQ NL 0)
  (WHILE (/= NL L)
    (SETQ NL (+ NL 1))
    (SETQ NC 0) (SETQ COLUMNA 0)
    (WHILE (/= NC C)
      (SETQ NC (+ NC 1))
      (SETQ CLAVE (STRCAT (ITOA NL) "-" (ITOA NC)))
      (SETQ EI (SUMA EII COLUMNA (* TAM (- L NL) 2)))
      (SETQ PBI (POLAR EI 0.785398 (/ TAM 1.2)))
      (IF (OR (= (ATOF (CDR (ASSOC CLAVE DATOSlp))) 0) (= NC 50))
        (COMMAND "INSERT" (STRCAT RUTA "BLOCKS\\TEXTO.DWG") PBI "" "" "")
        (COMMAND "INSERT" (STRCAT RUTA "BLOCKS\\NUMERO.DWG")
           (SUMA PBI (- (* (NTH (- NC 1) LONCOLS) TAM) 1) 0)
           "" "" ""
        )
      )
      (SETQ TM (* TAM 25))
      (SETQ BLOQUE (ENTLAST))
      (COMMAND "EXPLODE" BLOQUE)
      (SETQ GPOLINTOPF (SSADD (SSNAME (SSGET "L") 0) GPOLINTOPF))
      (SETQ E (ENTLAST))
      (ENTMOD (SUBST (CONS 1 (CDR (ASSOC CLAVE DATOSlp)))
                     (ASSOC 1 (ENTGET E))
                     (ENTGET E)
              )
      )
      (SETQ COLUMNA (+ COLUMNA (NTH (- NC 1) LONCOLS)))
    )
  )
)

(DEFUN SECUENCIA ()
  (LEELP)
  (LINEAS)
  (COLOCA)
  (SUPERFICIE)
)

(DEFUN TABLA ()
  (IF (SETQ TBL (OPEN "c:\\LINTOP" "r"))
    (SECUENCIA)
    (PRINC "EL ARCHIVO NO EXISTE EN EL DIRECTORIO ")
  )
  (command "ZOOM" "e")
  (command "SCALE" GPOLINTOPF "" eii esc)
)

(defun formato (datang)
  (write-line datang)
  (if (/= 1 (strlen datang))
    (progn
      (setq cuca 1)
      (while (/= cuca (strlen datang))
        (setq cara (substr datang cuca 1))
        (if (= "d" cara)
          (progn
            (setq t1 (substr datang 1 (- cuca 1)))
            (setq t2 (substr datang (+ cuca 1)))
            (setq datang2 (strcat t1 "%%d" t2))
          )
        )
        (setq cuca (+ cuca 1))
      )
    )
    (setq datang2 datang)
  )
  (setq datang datang2)
)


(defun cierra ()
  (setq puntoa p)
  (setq xa (car puntoa))
  (setq ya (car (cdr puntoa)))
  (setq d (rtos (distance punto puntoa) 2 3))
  (setq a (angtos (angle punto puntoa)))
  (setq aa (formato a))
  (setq est numpun)
  (setq pv numpun1)
  (setq renglon (strcat est "," pv "," d "," aa "," (rtos xa 2 3) "," (rtos ya 2 3)))
  (write-line renglon arch)
  (if (OR (= opacota "1") (= OPACOTA 1))
   (progn
    (command "INSERT" (STRCAT RUTA "BLOCKS\\COTA.DWG") (polar puntoa (angle puntoa punto) (/ (atof d) 2)) esc "" a "" "")
    (SETQ ENTP(ENTLAST))
    (SETQ ENTP(ENTNEXT ENTP))
    (COMMAND "ATTEDIT" "" "" "" "" ENTP "V" "R" D "") 
   )
  )
)

(defun datosg ()
  (setq punto (list x1 y1))
  (setq puntoa (list xa ya))
  (setq d (rtos (distance punto puntoa) 2 3))
  (setq a (angtos (angle puntoa punto)))
  (setq aa (formato a))
  (setq est numpuna)
  (setq pv numpun)
  (setq renglon (strcat est "," pv "," d "," aa "," (rtos x1 2 3) "," (rtos y1 2 3)))
  (write-line renglon arch)
  (if (OR (= opacota "1") (= OPACOTA 1))
   (progn
    (command "INSERT" (STRCAT RUTA "BLOCKS\\COTA") (polar punto (angle punto puntoa) (/ (atof d) 2)) esc "" a "" "")
    (SETQ ENTP(ENTLAST))
    (SETQ ENTP(ENTNEXT ENTP))
    (COMMAND "ATTEDIT" "" "" "" "" ENTP "V" "R" d "")
   )
  )
)

(defun c:lp ()
  (command "undo" "m")
  (COMMAND "VIEW" "S" "PROV")
  (C:LIBRERIA "BUSCA VALOR DE ATRIBUTO")
  (SETQ OPCIONESOS (GETVAR "OSMODE"))
  (command "osnap" "none")
  (COMMAND "LUNITS" 2)
  (COMMAND "LUPREC" 3)
  (COMMAND "AUNITS" 4)
  (COMMAND "AUPREC" 4)
  (COMMAND "ANGDIR" 0)
  (COMMAND "ANGBASE" 0.0)
  (command "layer" "M" "automatico" "")
  (command "layer" "M" "cotas" "")
  (setq arranque 1000)
  (setq ARCcfg (open (strcat ruta "configuraciones de programas\\lintopf.CFG") "r"))
  (IF (= ARCcfg NIL)
   (PROGN
    (SETQ opacota "1")
    (SETQ ESCc 1.00)
    (SETQ OPbav "1")
    (SETQ OPpdesf "1")
    (SETQ OPip "0")
    (SETQ OPcrcu "1")
    (setq nottexto "1")
    (setq noterr "1")
    (setq notadj "0")
   )
   (PROGN
    (setq opacota (read-line arCcfg))
    (setq ESCc (read-line arccfg))
    (if (/= escc nil)
      (SETQ ESCc (ATOF ESCc))
      (SETQ ESCc 1.0)
    )
    (setq opbav (read-line arCcfg))
    (setq oppdesf (read-line arccfg))
    (setq opip (read-line arCcfg))
    (setq opcrcu (read-line arCcfg))
    (setq nottexto (read-line arccfg))
    (setq Noterr (read-line arCcfg))
    (setq Notadj (read-line arCcfg))
    (IF (= opacota NIL) (SETQ opacota "1"))
    (IF (= opbav NIL) (SETQ opbav "1"))
    (IF (= oppdesf NIL) (SETQ oppdesf "1"))
    (IF (= opip NIL) (SETQ opip "0"))
    (IF (= opcrcu NIL) (SETQ opcrcu "1"))
    (IF (= nottexto NIL) (SETQ nottexto "1"))
    (IF (= noterr NIL) (SETQ noterr "1"))
    (IF (= notadj NIL) (SETQ notadj "0"))
    (CLOSE ARCcfg)
   )
  )
  (setq oppr (getstring "\n Deseas cambiar la configuracion o solo seleccionar la Polylinea (C/P) <P>:"))
  (if (or (= oppr "") (= oppr nil))
    (setq oppr "pl")
  )
  (if (= (strcase oppr) "C")
   (progn
    (setq dcl_id (load_dialog (strcat ruta "dialogos\\lintopf.dcl"))) ; Load the DCL file.
    (if (not (new_dialog "lintopf" dcl_id))   
      (exit)                                
                                           
    )
    (set_tile "t" opacota)
    (set_tile "Sblock" (rtos Escc 2 3))
    (set_tile "t1" opbav)
    (set_tile "t2" oppdesf)
    (set_tile "t3" opip)
    (set_tile "t4" opcrcu)
    (set_tile "t5" nottexto)
    (set_tile "t6" noterr)
    (set_tile "t7" notadj)
    (action_tile "accept" "(leevar)")
    (action_tile "cancel" "(exit)")
    (start_dialog)                          
                                            
    (unload_dialog dcl_id)                  
    (princ)
   )
  )

(IF (/= X "LLAMA")
 (PROGN
  (setq lin (car (entsel "\n Selecciona la polylinea a procesar: ")))
  (COMMAND "AREA" "E" LIN)
  (while (/= "LWPOLYLINE" (cdr (assoc 0 (entget lin))))
      (if (/= "LWPOLYLINE" (cdr (assoc 0 (entget lin))))
        (progn   
          (alert "\nEl objeto debe ser polylinea ")
          (setq lin (car (entsel "\n Selecciona objeto: ")))
        )
      )
  )
 )
 (COMMAND "AREA" "E" LIN)
)
  (if  (= Nottexto "1")
    (setq esc (getreal (strcat "\n Escala del texto <" (rtos escc 2 3) "> ")))
  )
  (if (= esc nil) (setq esc escc))
  (setq ARCcfg (open (strcat ruta "configuraciones de programas\\lintopf.CFG") "w"))
  (write-line opacota arccfg)
  (write-line (rtos escC 2 3) arccfg)
  (write-line opbav arccfg)
  (write-line oppdesf arccfg)
  (write-line opip arccfg)
  (write-line opcrcu arccfg)
  (write-line nottexto arccfg)
  (write-line noterr arccfg)
  (CLOSE ARCcfg)
  (setq arch (open "c:\\lintop" "w"))
  (setq renglon "EST.,P.V.,DISTANCIA, RUMBO,   X,   Y")
  (if  (= opbav "1")
    (MPUN LIN)
  )
  (write-line renglon arch)
  (setq nop 1)
  (setq lista (entget lin))
  (setq xa nil)
 (while lista
    (setq elemento (car lista))
    (if (= 10 (car elemento))
      (progn 
        (setq p1 (cdr elemento))
        (setq gnupo (ssget "C" (suma p1 0.01 0.01) (suma p1 -0.01 -0.01)))
        (setq conta 0)
        (setq enco 0)
        (while (/= conta (sslength gnupo))
          (setq nnupo (ssname gnupo conta))
          (SETQ PV (cdr (assoc 10 (entget nnupo))))
          (SETQ XV (CAR PV))
          (SETQ YV (CADR PV))
          (SETQ X1 (CAR P1))
          (SETQ Y1 (CADR P1))
          (SETQ NOMBREP (cdr (assoc 2 (entget nnupo))))
          (if (OR (= "PUNTO" NOMBREP) (= "pun2" NOMBREP) (= "PUN2" NOMBREP) (= "punto" NOMBREP))
            (IF (AND (= (RTOS XV 2 2) (RTOS X1 2 2)) (= (RTOS YV 2 2) (RTOS Y1 2 2)))
              (progn
                (setq enco 1)
                (setq conta (- (sslength gnupo) 1))
              )
            )
          )
          (setq conta (+ conta 1))
        )
        (if (= enco 1)
          (progn
            (setq numpun (busatr NNUPO "PUNTO"))
            (setq espu (cdr (assoc 41 (entget nnupo))))
          )
          (progn
          (if (/= opip "1")
           (progn
            (write-line " Vertice sin asignacion de punto; procediendo con asigmacion automatica: ")
            (ALERT "NO SE ENCONTRO BLOCK EN UN VERTICE")
            (COMMAND "VIEW" "S" "MSA")
            (COMMAND "ZOOM" "C" P1 "10")
            (COMMAND "CIRCLE" P1 ".1")
            (SETQ PROVE (ENTLAST))
            (setQ OPT2 (GETSTRING "DESEAS /I-nsertar/S-eleccionar/ EL BLOCK (I/S) <I> :"))
            (IF (= "CIRCLE" (cdr (assoc 0 (ENTGET PROVE))))
              (COMMAND "ERASE" PROVE "")
            )
            (COMMAND "VIEW" "R" "MSA")
           )
           (setq opt2 "I")
          )
            (IF (= OPT2 "")
               (SETQ OPT2 "I") 
            )
           (IF (= (STRCASE OPT2) "I")
            (PROGN
             (if (/= opip "1")
              (progn
               (setQ OPT3 (GETREAL (STRCAT "NUMERO DE PUNTO A INSERTAR <"(RTOS (1+ ARRANQUE) 2 0) "> :")))
               (IF (/= OPT3 NIL)
                  (SETQ ARRANQUE (1- OPT3)) 
               )                      
              )
             )
              (if (= espu nil) (setq espu 1))
              (command "INSERT" (STRCAT RUTA "BLOCKS\\PUNTO") p1 espu "" "" (rtos (+ arranque 1) 2 0)  "AUTOMATICO" "" "")
              (command "CHANGE" (entlast) "" "P" "LA" "AUTOMATICO" "")
              (setq arranque (+ arranque 1))
              (setq numpun (rtos arranque 2 0))
            )
            (PROGN 
              (setq PROVE (car (entsel "Selecciona el bloque a MOVER: ")))
              (command "MOVE" PROVE "" (cdr (assoc 10 (entget PROVE))) P1)
             ) 
            )
           )
        )
        (setq x1 (car p1))
        (setq y1 (car (cdr p1)))
        (if xa
          (progn
            (setq nop (+ nop 1))
            (datosg)
          )
          (progn
            (setq p p1)
            (setq x x1)
            (setq y y1)
            (setq numpun1 numpun)
          )
        )
        (setq xa x1)
        (setq ya y1)
        (setq numpuna numpun)
      )
    )
    (setq lista (cdr lista))
  )
  (cierra)
  (close arch)
  (if (= opcrcu "1")
    (tabla)
  )
  (SETQ OP "")
 (if (= notadj "1")
  (WHILE (/= OP "S")
    (SETQ OP (GETSTRING "EL TAMA¥O Y POSICION DE LA TABLA ES CORRECTO (S/N) <S>:"))
    (IF (= OP "")
      (SETQ OP "S")
    )
    (IF (/= (STRCASE OP) "S")
     (PROGN
      (SETQ OP2 (GETSTRING "DESEAS MOVER O ESCALAR LA TABLA (M/S) <S>:"))
      (IF (= OP2 "")
        (SETQ OP2 "S")
      )
      (IF (= OP2 "S")
        (PROGN
          (SETQ FS (GETSTRING "FACTOR DE ESCALA :"))
          (command "ZOOM" "e")
          (COMMAND "SCALE" GPOLINTOPF "" EII FS)
        )
        (PROGN
          (SETQ FS (GETPOINT "PUNTO DESTINO DEL CUADRO :"))
          (COMMAND "MOVE" GPOLINTOPF "" EII FS)
          (SETQ EII FS)
        )
      )
     )
    )
  )
 )
  (COMMAND "VIEW" "R" "PROV")
  (SETVAR "OSMODE" OPCIONESOS)
)

(DEFUN MPUN (POLI)
  (SETQ PROV 1)
  (SETQ P1T (VERTICE POLI PROV))
  (SETQ XMENOR (CAR P1T))
  (SETQ YMENOR (CADR P1T))
  (SETQ XMAYOR XMENOR)
  (SETQ YMAYOR YMENOR)
  (SETQ PROVV P1T)
  (while p1t
    (SETQ X2PROV (CAR P1T))
    (SETQ Y2PROV (CADR P1T))
    (IF (AND (< X2PROV XMENOR) (/= X2PROV nil)) (SETQ XMENOR X2PROV))
    (IF (AND (< Y2PROV YMENOR) (/= Y2PROV nil)) (SETQ YMENOR Y2PROV))
    (IF (AND (> X2PROV XMAYOR) (/= X2PROV nil)) (SETQ XMAYOR X2PROV))
    (IF (AND (> Y2PROV YMAYOR) (/= Y2PROV nil)) (SETQ YMAYOR Y2PROV))
    (SETQ PROV (1+ PROV))
    (SETQ P1T (VERTICE POLI PROV))
  )
  (COMMAND "ZOOM" "W" (STRCAT (RTOS XMENOR 2 6) "," (RTOS YMENOR 2 6)) (STRCAT (RTOS XMAYOR 2 6) "," (RTOS YMAYOR 2 6)))  
  (REDRAW POLI 3)
  (SETQ PROV 1)
  (SETQ P1T (VERTICE POLI PROV))
  (WHILE P1T
    (setq gpoLP (ssget "C" (suma p1T 0.10 0.10) (suma p1T -0.10 -0.10)))
    (SETQ R (sslength gpoLP))
    (SETQ PROV2 0)
    (setq mdist 100)
    (SETQ OBCOR NIL)
    (REPEAT R
      (SETQ OBJP (ssname gpoLP PROV2))
      (if (= "PUNTO" (cdr (assoc 2 (entget OBJP))))
       (progn
        (SETQ PVT (cdr (assoc 10 (entget OBJP))))
        (setq pdist (distance p1T pvT))
        (if (> mdist pdist)
         (progn
          (setq mdist pdist)
          (setq obcor objP)
         )
        )
       )
      )
      (SETQ PROV2 (1+ PROV2))
    )
    (if (AND (< 0 MDIST) (/= obcor nil))
    (if (= noterr "1")
     (IF (> MDIST 0.01)
      (PROGN
       (ALERT "HAY UN BLOCK FUERA DE SU POSICION")
       (SETQ XYZ (cdr (assoc 10 (ENTGET OBCOR))))
       (COMMAND "ZOOM" "C" XYZ "4")
       (COMMAND "CIRCLE" XYZ ".1")
       (SETQ PROVE (ENTLAST))
       (setQ OPT (GETSTRING "DESEAS MOVERLO HACIA LA LINEA (S/N) <S> :"))
       (IF (= "CIRCLE" (cdr (assoc 0 (ENTGET PROVE))))
         (COMMAND "ERASE" PROVE "")
       )
       (IF (= OPT "")
          (SETQ OPT "S") 
       )
       (IF (= OPT "S")
        (PROGN
         (command "MOVE" OBCOR "" (cdr (assoc 10 (entget OBCOR))) P1T)
        )
       )
       (COMMAND "ZOOM" "P")
      )
     )
      (if (= oppdesf "1")
        (command "MOVE" OBCOR "" (cdr (assoc 10 (entget OBCOR))) P1T)
      )
     )
    )
    (SETQ PROV (1+ PROV))
    (SETQ P1T (VERTICE POLI PROV))
    (IF (AND (/= P1T NIL) (/= PROVV NIL))
     (PROGN
      (setq pRdist (distance p1T PROVV))
      (IF (= PRDIST 0)
       (PROGN
        (ALERT "TIENES UNA DISTANCIA 'CERO' EN DOS VERTICES DISTINTOS")
        (command "ZOOM" "C" P1T 10)
        (COMMAND "CIRCLE" P1T "5")
        (FINISH)
       )
      )
      (SETQ PROVV P1T)
     )
    )
  )         
)

(defun vertice (poli nov)
  (setq listap (entget poli))
  (setq nver 0)
  (setq salir "N")
  (while (= salir "N")
    (setq sublisp (car listap))
    (if (= 10 (car sublisp))
      (progn
        (setq punto (cdr sublisp))   
        (setq nver (+ nver 1))
      )
    )
    (setq listap (cdr listap))
    (if listap
      (setq salir "N")
      (setq salir "S")
    )
    (if (= nov nver)
      (setq salir "S")
    )
  )
  (if (not listap)
    (setq punto nil)
  )
  (setq punto punto)
)

(DEFUN SUPERFICIE ()
   (IF (= DESC nil) (SETQ DESC "POLIGONO GENERAL"))
   (SETQ DESC2 (GETSTRING PROMPT (STRCAT "\n DESCRIPCION DEL POLIGONO <" DESC ">")))
   (IF (/= DESC2 "")
     (SETQ DESC DESC2)
   )
   (SETQ Y (+ (CADR (POLAR EII 1.5708 (* TAM 2 L))) 0.589))
   (SETQ X (CAR eii))
   (setq inseR (strcat (RTOS (+ X (/ DIST 2)) 2 3) "," (RTOS Y 2 3)))
   (COMMAND "INSERT" (STRCAT RUTA "BLOCKS\\TEXTC") INSER "" "" "")
   (SETQ BLOQUE (ENTLAST))
   (COMMAND "EXPLODE" BLOQUE)
   (SETQ GPOLINTOPF (SSADD (SSNAME (SSGET "L") 0) GPOLINTOPF))
   (COMMAND "CHANGE" "L" "" "" "" "" "" "" (STRCAT "CUADRO DE CONSTRUCCION " DESC))
   (SETQ Y (- (CAR (CDR EII)) 1.411))
   (setq inseR (strcat (RTOS (+ X (/ DIST 2)) 2 3) "," (RTOS Y 2 3)))
   (COMMAND "INSERT" (STRCAT RUTA "BLOCKS\\TEXTC") INSER "" "" "")
   (SETQ BLOQUE (ENTLAST))
   (COMMAND "EXPLODE" BLOQUE)
   (SETQ GPOLINTOPF (SSADD (SSNAME (SSGET "L") 0) GPOLINTOPF))
   (COMMAND "CHANGE" "L" "" "" "" "" "" "" (STRCAT "SUPERFICIE " DESC " = " (RTOS (GETVAR "AREA") 2 3) " m2"))
)

(defun leevar ()
  (setq opacota (get_tile "t"))
  (setq escc (atof (get_tile "Sblock")))
  (setq opbav (get_tile "t1"))
  (setq oppdesf (get_tile "t2"))
  (setq opip (get_tile "t3"))
  (setq opcrcu (get_tile "t4"))
  (setq nottexto (get_tile "t5"))
  (setq noterr (get_tile "t6"))
  (setq notadj (get_tile "t7"))
  (done_dialog)
)
