(DEFUN SUMA (P VX VY)
  (SETQ X (CAR P))
  (SETQ Y (CAR (CDR P)))
  (LIST (+ X VX) (+ Y VY) (LAST P))
)

(defun equis ()
  (if (< xmayor (atof dat))
    (setq xmayor (atof dat))
  )
  (if (> xmenor (atof dat))
    (setq xmenor (atof dat))
  )
)

(defun ye ()
  (if (< ymayor (atof dat))
    (setq ymayor (atof dat))
  )
  (if (> ymenor (atof dat))
    (setq ymenor (atof dat))
  )
)


(DEFUN COLUMNAS ()
  (SETQ CA (SUBSTR LIN 1 1))
  (SETQ C 0) (SETQ X 1)
  (setq xmayor 0) (setq xmenor 0) (setq ymayor 0) (setq ymenor 0)
  (WHILE (/= C 3)
    (SETQ C (+ C 1))
    (SETQ DAT "")
    (WHILE (/= CA ",")
      (SETQ X (+ X 1))
      (SETQ DAT (STRCAT DAT CA))
      (SETQ CA (SUBSTR LIN X 1))
    )
    (SETQ CA "")
    (if (= c 1)
      (equis)
    )
    (if (= c 2)
      (ye)
    )
  )
)


(DEFUN LEE ()
  (SETQ LIN (READ-LINE arch))
  (SETQ L 1)
  (LEEINI)
  (WHILE (AND LIN (<= L FIN))
    (COLUMNAS)
    (SETQ L (+ L 1))
    (SETQ LIN (READ-LINE arch))
  )
  (SETQ L (- L 1))
)

(defun camatr ()
  (setq atrib (cdr (assoc 2 (entget ent))))
  (setq nocol (cdr (assoc atrib datos)))
  (setq valor (cdr (assoc nocol atributos)))
  (entmod (subst (cons 1 valor)
                 (assoc 1 (entget ent))
                 (entget ent)
          )
  )
)

(defun cambiaatr ()
  (setq ent (entlast))
  (while ent
    (if (= "ATTRIB" (cdr (assoc 0 (entget ent))))
      (camatr)
    )
    (setq ent (entnext ent))
  )
)

(DEFUN COLUMNAS2 ()
  (SETQ CA (SUBSTR LIN 1 1))
  (SETQ C 0) (SETQ X 1)
  (SETQ ATRIBUTOS NIL)
  (WHILE (/= C (+ noatri 3))
    (SETQ C (+ C 1))
    (SETQ DAT "")
    (SETQ SALIR "N")
    (WHILE SALIR
      (SETQ X (+ X 1))
      (SETQ DAT (STRCAT DAT CA))
      (SETQ CA (SUBSTR LIN X 1))
      (IF (= CA ",")
        (SETQ SALIR nil)
      )
      (IF (= CA "")
        (SETQ SALIR nil)
      )
    )
    (SETQ CA "")
    (setq atributo (cons c dat))
    (setq atributos (append atributos (list atributo)))
  )
  (IF (= "3" TRI)
;  (ENTMAKE (LIST '(0 . "TEXT") '(100 . "AcDbEntity") layert '(100 . "AcDbBlockReference") (2 . "PUN2") XYZX tamanot TEXTX colorcot))
;  (ENTMAKE (LIST '(0 . "INSERT") '(100 . "AcDbEntity") '(8 . "0") '(100 . "AcDbBlockReference") (2 . "PUN2") (10 0 0 0) (41 . 1)))
    (COMMAND "COPY" UL "" (LIST ex ey) (LIST (ATOF (CDR (ASSOC 1 ATRIBUTOS)))
                                             (ATOF (CDR (ASSOC 2 ATRIBUTOS)))
                                             (ATOF (CDR (ASSOC 3 ATRIBUTOS)))))
    (COMMAND "COPY" UL "" (LIST ex ey) (LIST (ATOF (CDR (ASSOC 1 ATRIBUTOS)))
                                             (ATOF (CDR (ASSOC 2 ATRIBUTOS)))))
  )
  (cambiaatr)
  (SETQ CODIGOA CODIGO)
  (SETQ PA P)
  (SETQ P (STRCAT (CDR (ASSOC 1 ATRIBUTOS)) "," (CDR (ASSOC 2 ATRIBUTOS))))
  (SETQ CODIGO (CDR (ASSOC 5 ATRIBUTOS)))
  (SETQ CODIGOP (SUBSTR CODIGO 1 5))
  (if (or (= codigoP "arbol") (= codigoP "ARBOL"))
     (COMMAND "INSERT" (STRCAT RUTA "BLOCKS\\ARBOL.dwg") P "" "" "")
  )                         ' INSERTA ARBOL
  (IF (= CODIGO CODIGOA) (SETQ LPROV "1"))
  (IF (/= LPROV NIL)
    (if (= union "1")
      (IF (AND (= CODIGO CODIGOA) (/= CODIGOP "ARBOL") (/= CODIGO "Z") (/= CODIGO "EST"))
        (UNE)
;        (UNESEG)
      )
    )
  )
)

(DEFUN LEEINI ()
 (if (/= oldop "todo")
  (progn
   (WHILE (< L INI)
     (SETQ L (+ L 1))
     (SETQ LIN (READ-LINE arch))
   )
   (SETQ LIN (READ-LINE arch))
  )
 )
)

(DEFUN LEE2 ()
  (SETQ LIN (READ-LINE arch))
  (SETQ L 1) (setq atributos nil)
  (LEEINI)
  (if (/= oldop "todo")
    (WHILE (AND LIN (<= L FIN))
      (COLUMNAS2)
      (SETQ L (+ L 1))
      (SETQ LIN (READ-LINE arch))
    )
    (WHILE LIN 
      (COLUMNAS2)
      (SETQ LIN (READ-LINE arch))
    )
  )
  (SETQ L (- L 1))
)

(defun proatrib ()
  (setq noatri (+ noatri 1))
  (setq nomatr (cdr (assoc 2 (entget e))))
  (print nomatr)
  (IF (= 1 NOATRI)
    (SETQ K 5)
  )
  (IF (= 2 NOATRI)
    (SETQ K 3)
  )
  (IF (= 3 NOATRI)
    (SETQ K 4)
  )
;  (IF (= OPINSAT 0)
    (SETQ COLUMNA K)
;    (setq columna (getint (STRCAT " No. de columna para este atributo <" (ITOA K) "> : ")))
;  )
;  (IF (= COLUMNA NIL) 
;    (SETQ COLUMNA K)
;  )
  (setq dato (cons nomatr columna))
  (setq datos (append datos (list dato)))
)

(defun abloque ()
  (setq e (cdr (assoc -2 lisblo)))
  (setq noatri 0) (setq datos nil)
  (while e
    (if (= "ATTDEF" (cdr (assoc 0 (entget e))))
      (PROATRIB)
    )
    (setq e (entnext e))
  )
  (print noatri)
)

(defun contINS ()
  (COMMAND "UNDO" "M")
;  (COMMAND "UNDO" "begin")
  (COMMAND "REGENAUTO" "OFF")
  (if (= fechains nil)
    (progn
      (COMMAND "SHELL" (strcat RUTA "fecha2.exe"))
      (command "delay" 100)
      (setq fechains "y")
    )
  )
  (C:LIBRERIA "busca block en base de datos")
  (C:LIBRERIA "Carga blocks a pplt")
  (C:LIBRERIA "Carga LAYERs a pplt")
  (C:LIBRERIA "lee valor de texto de pplt")
  (C:LIBRERIA "BUSCA LAYER EN BASE DE DATOS")
  (C:LIBRERIA "lee valor numerico de pplt")
  (C:LIBRERIA "carga attributos a lista")
  (C:LIBRERIA "Carga atributos de un block a pplt")
  (C:LIBRERIA "SEPARA VALORES DE COMAS DE UN TEXTO TO LISTA")
  (C:LIBRERIA "SEPARA VALORES DE ESPACIOS DE UN TEXTO TO LISTA")
  (C:LIBRERIA "SEPARA VALORES DE TABULACIONES DE UN TEXTO TO LISTA")
  (command "layer" "M" "LINEAS" "C" "GREEN" "LINEAS" "")
  (SETQ VALIDA (SBLBD "PUN2"))
    (If (/= VALIDA "S") 
      (PROGN 
       (COMMAND "INSERT" (STRCAT RUTA "BLOCKS\\PUN2.dwg") "0,0" "" "" "" "" "" "" "" "" "")
       (COMMAND "ERASE" (ENTLAST) "")
      )
    )
  (SETQ VALIDA (SBLBD "PUNTO"))
    (If (/= VALIDA "S") 
      (PROGN 
       (COMMAND "INSERT" (STRCAT RUTA "BLOCKS\\PUNTO.dwg") "0,0" "" "" "" "" "" "" "" "" "")
       (COMMAND "ERASE" (ENTLAST) "")
      )
    )
  (setq ARCINSAT (open (strcat ruta "configuraciones de programas\\INSATR.CFG") "r"))
  (IF (= ARCINSAT NIL)
   (PROGN
    (SETQ NBLOCK "PUN2")
    (SETQ ESCB 1.00)
    (SETQ ARCHIVOP "c:\\TOPOGRAF\\PROV.CSV")
    (SETQ RI 1)
    (SETQ RF 1000)
    (SETQ DIMEN "2")
   )
   (PROGN
    (setq NBLOCK (read-line arCINSAT))
    (setq ESCB (read-line arcINSAT))
    (if (/= escb nil)
      (SETQ ESCB (ATOF ESCB))
      (SETQ ESCB 1.0)
    )
    (setq ARCHIVOP (read-line arCINSAT))
    (setq RI (read-line arcINSAT))
    (if (/= ri nil)
      (SETQ RI (ATOI RI))
      (SETQ RI 1)
    )
    (setq RF (read-line arcINSAT))
    (if (/= rf nil)
      (SETQ Rf (ATOI Rf))
      (SETQ Rf 1000)
    )
    (setq DIMEN (read-line arCINSAT))
    (IF (= Nblock NIL) (SETQ Nblock "pun2"))
    (IF (= archivop NIL) (SETQ archivop "c:\\topograf\\prov.csv"))
    (IF (= dimen NIL) (SETQ dimen "2"))
    (CLOSE ARCINSAT)
   )
  )
  (SETQ VALIDA (SBLBD nblock))
    (If (/= VALIDA "S") 
      (PROGN 
       (COMMAND "INSERT" (STRCAT RUTA "BLOCKS\\" nblock) "0,0" "" "" "" "" "" "" "" "" "")
       (COMMAND "ERASE" (ENTLAST) "")
      )
    )
  (setq NOMARCH (getfiled "ARCHIVO DE DATOS" ARCHIVOP "CSV" 32))
  (if (= NOMARCH NIL)
    (exit)
  )
  (setq archivop nomarch)
  (VALIDAFILE)
  (setq ARCdate (open (strcat ruta "date.tmp") "r"))
  (setq fecha (read-line arcdate))
  (close arcdate)
  (SETQ OPDATOSBL NIL)
  (AtrToList nblock)
  (setq dcl_id (load_dialog (strcat ruta "dialogos\\insatr.dcl"))) ; Load the DCL file.
  (if (not (new_dialog "insatr" dcl_id))   ; Initialize the dialog.
    (exit)                                ; Exit if this doesn't 
                                          ; work.
  )
(alert "llegue")
  (setq numerofinallista (ldblpp "Nblock"))
  (setq numerofinallista2 (ldlApp "Nlayer"))
  (if (= (strcase nblock) "PUN2")
    (set_tile "Nblock" "0")
  )
  (SET_TILE "Nlayer" (itoa (rnnpp (getvar "CLAYER") (strcat ruta "PROVL.TMP"))))
  (set_tile "Arcf" archivop)
  (set_tile "Nblock" nblock)
  (set_tile "Sblock" (rtos Escb 2 3))
  (set_tile "Old" "1")
  (set_tile "tag2" "1")
  (set_tile "une" "1")
  (set_tile "layer2" "1")
  (set_tile "fecha" fecha)
  (mode_tile "Iniciol" 1)
  (mode_tile "finl" 1)
  (mode_tile "tag1" 1)
  (mode_tile "tag2" 1)
  (mode_tile "Cadena" 1)
  (set_tile "Iniciol" (itoa RI))
  (set_tile "finl" (itoa RF))
  (if (/= dimen "2")
     (set_tile "tres" "1")
     (set_tile "dos" "1")
  )
  (action_tile "Nblock" "(camlistbl)")
  (action_tile "examinaf" "(examinaf2)")
  (action_tile "Old2" "(mode_tile_on)")
  (action_tile "Old" "(mode_tile_off)")
  (action_tile "layer1" "(mode_tile_l1)")
  (action_tile "camcolor" "(cambiacolor)")
;  (action_tile "color" "(leecolor "1")")
  (action_tile "layer2" "(mode_tile_l2)")
  (action_tile "tag1" "(st_tile_pr)")
  (action_tile "tag2" "(st_tile_pr)")
  (action_tile "Cadena" "(st_tile_pr)")
  (action_tile "examina" "(examinaf)")
  (action_tile "attrib" "(attributo)")
  (action_tile "accept" "(leevar)")
  (action_tile "cancel" "(exit)")
  (start_dialog)                          ; Display the dialog 
                                          ; box.
  (unload_dialog dcl_id)                  ; Unload the DCL file.
  (princ)
  (if (= oplayer "1")
    (command "layer" "M" nombrelmk "" "s" nombrelmk "")
    (command "layer" "s" nlayer "")
  )

  (setq ex 1.13)
  (setq ey 1.13) 
  (setq tt ESCB)
    (SETQ OPCIONESOS (GETVAR "OSMODE"))
    (command "osnap" "none")
    (SETQ VALIDA (SBLBD (STRCASE nomblo)))
    (IF (/= "S" VALIDA) (SETQ VALIDA (SBLBD NOMBLO)))
    (If (/= VALIDA "S") 
      (PROGN 
       (if (= (substr nomblo 2 1) ":")
         (COMMAND "INSERT" nomblo "0,0" "" "" "" "" "" "" "" "" "" "" "" "" "" "" "")
         (COMMAND "INSERT" (STRCAT RUTA "BLOCKS\\" nomblo ".dwg") "0,0" "" "" "" "" "" "" "" "" "" "" "" "" "" "" "")
       )
       (setq nomblo (cdr (assoc 2 (entget (entlast)))))
       (COMMAND "ERASE" (ENTLAST) "")
      )
    )
  (command "INSERT" nomblo (list ex ey) tt "" ""
   "" "" "" "" "" "" "" "" "" "" "" "" "" "" "" "" "" "" "" "" "" "" "" ""
   "" "" "" "" "" "" "" "" "" "" "" "" "" "" "" "" "" "" "" "" "" "" "" "")
  (SETQ UL (ENTLAST))
  (IF (/= resultado8 "1")
    (setq TRI "3")
    (setq TRI "2")
  )
  (IF (= resultado4 "1")
    (setq oldop "todo")
    (setq oldop "bloque")
  )
  (setq ARCINSAT (open (strcat ruta "configuraciones de programas\\INSATR.CFG") "w"))
  (WRITE-LINE NOMBLO ARCINSAT)
  (WRITE-LINE (RTOS tt 2 3) ARCINSAT)
  (WRITE-LINE ARCHIVOP ARCINSAT)
  (WRITE-LINE (RTOS INI 2 3) ARCINSAT)
  (WRITE-LINE (RTOS FIN 2 3) ARCINSAT)
  (WRITE-LINE tri ARCINSAT)
  (CLOSE ARCINSAT)
;  (setq lisblo (tblsearch "block" nomblo))
;  (ABLOQUE)
;  (IF (/= (SUBSTR ARCHIVOP 1 1) (CHR 34)))
;    (SETQ ARCHIVOP (STRCAT (CHR 34) ARCHIVOP (CHR 34)))
;  )
  (setq arch (OPEN NOMARCH "r"))
  (if arch
    (LEE)
    (print "\n Archivo no encontrado ")
  )
  (close arch)
;  (command "ZOOM" "w" (list xmayor ymayor) (list xmenor ymenor))
  (setq arch (OPEN NOMARCH "r"))
  (if arch
    (LEE2)
  )
  (close arch)
  (entdel ul)
  (SETVAR "OSMODE" OPCIONESOS)
  (command "ZOOM" "E")
  (COMMAND "REGENAUTO" "ON")
;  (COMMAND "UNDO" "end")
)

(defun c:insat ()
  (SETQ CODIGOA "")
  (SETQ CODIGO "")
  (SETQ LPROV NIL)
  (contINS)
)

(defun examinaf ()
  (setq archbl (getfiled "Block a insertar" (strcat ruta "blocks\\" nblock ".dwg") "dwg" 32))
  (WHILE (= ARCHBL NIL)
    (setq ARCHBL (getfiled "Block a insertar" (strcat ruta "blocks\\" nblock ".dwg") "DWG" 32))
  )
  (start_list "Nblock" 2)
  (add_list archbl)
  (end_list)
  (setq archdim (open (strcat ruta "prov.tmp") "a"))
  (write-line archbl archdim)
  (close archdim)
  (set_tile "Nblock" (itoa numerofinallista))
  (setq numerofinallista (1+ numerofinallista))
)

(defun examinaf2 ()
  (setq NOMARCH2 (getfiled "Archivo Fuente" ARCHIVOP "CSV" 32))
  (WHILE (= NOMARCH2 NIL)
    (setq NOMARCH2 (getfiled "SELECCIONA EL ARCHIVO DE DATOS" ARCHIVOP "CSV" 32))
  )
  (setq NOMARCh NOMARCH2)
  (setq ARCHIVOP NOMARCH2)
  (set_tile "Arcf" Nomarch)
  (validafile)
)

(defun leevar ()
;  (setq nomarch (get_tile "Arcf"))
  (setq nomblo (get_tile "Nblock"))
  (setq nomblo (rblpp (atoi nomblo) (strcat ruta "PROV.TMP")))
  (setq nly (get_tile "Nlayer"))
  (setq nlayer (rblpp (atoi nly) (strcat ruta "PROVl.TMP")))
  (setq escb (atof (get_tile "Sblock")))
  (setq resultado4 (get_tile "Old"))
  (setq ini (get_tile "Iniciol"))
  (setq ini (atoi ini))
  (setq fin (get_tile "finl"))
  (setq fin (atoi fin))
  (setq resultado8 (get_tile "dos"))
  (setq oplayer (get_tile "layer1"))
  (setq nombrelmk (get_tile "Prevcad"))
  (setq union (get_tile "une"))
  (done_dialog)
)

(defun mode_tile_on()
  (mode_tile "Iniciol" 0)
  (mode_tile "finl" 0)
)

(defun mode_tile_off()
  (mode_tile "Iniciol" 1)
  (mode_tile "finl" 1)
)

(defun mode_tile_l1 ()
  (mode_tile "tag1" 0)
  (mode_tile "tag2" 0)
  (mode_tile "Cadena" 0)
  (mode_tile "Nlayer" 1)
)

(defun mode_tile_l2 ()
  (mode_tile "tag1" 1)
  (mode_tile "tag2" 1)
  (mode_tile "Cadena" 1)
  (mode_tile "Nlayer" 0)
)

(defun st_tile_pr ()
  (setq cadprov "")
  (if (= (get_tile "tag1") "1")
    (setq cadprov fecha)
  )
  (if (= (get_tile "tag2") "1")
    (setq cadprov (strcat cadprov (get_tile "Cadena")))
  )
  (set_tile "Prevcad" cadprov)
  (SETQ OPPRV (BSLAYER cadprov))
  (if (= opprv "S") (alert "Nombre de layer repetido"))
)

(DEFUN UNE ()
  (command "LAYER" "S" "LINEAS" "")
  (COMMAND "PLINE" P PA "")
  (SETQ ULLI (ENTLAST))
  (setq paso 1)
;  (command "LAYER" "S" "0" "")
)

(DEFUN UNESEG ()
  (if (= paso 1)
    (COMMAND "PEDIT" ULLI "J" "ALL" "" "")
  )
)

(defun attributo ()
  (setq nomblox (get_tile "Nblock"))
  (setq nomblo (rblpp (atoi nomblox) (strcat ruta "PROV.TMP")))
  (AtrToList nomblo)
  (IF (/= OPDATOSBL NIL) (ABLOQUE))
  (setq arch (OPEN NOMARCH "r"))
  (setq linea1 (read-line arch))
  (setq linea2 (read-line arch))
  (setq linea3 (read-line arch))
  (setq linea4 (read-line arch))
  (setq linea5 (read-line arch))
  (setq linea6 (read-line arch))
  (setq linea7 (read-line arch))
  (setq linea8 (read-line arch))
  (setq linea9 (read-line arch))
  (setq linea10 (read-line arch))
  (close arch)
  (convierte)
  (if (not (new_dialog "insatr2" dcl_id))   ; Initialize the dialog.   2do dialogo
    (exit)                                ; Exit if this doesn't 
                                          ; work.
  )
  (setq numerofinallista (ldattpp "atr"))  
  (set_tile "t1" linea1)
  (set_tile "t2" linea2)
  (set_tile "t3" linea3)
  (set_tile "t4" linea4)
  (set_tile "t5" linea5)
  (set_tile "t6" linea6)
  (set_tile "t7" linea7)
  (set_tile "t8" linea8)
  (set_tile "t9" linea9)
  (set_tile "t10" linea10)
  (action_tile "atr" "(atrlist)")
  (action_tile "posa" "(valposa)")
  (action_tile "Tpar" "(tipoarc)")
  (start_dialog)                          ; Display the dialog 
  (if (not (new_dialog "insatr" dcl_id))   ; Initialize the dialog.
    (exit)                                ; Exit if this doesn't 
                                          ; work.
  )
  (setq numerofinallista (ldblpp "Nblock"))
  (setq numerofinallista2 (ldlApp "Nlayer"))
  (SET_TILE "Nlayer" (itoa (rnnpp (getvar "CLAYER") (strcat ruta "PROVL.TMP"))))
  (set_tile "Arcf" archivop)
  (set_tile "Nblock" nomblox)
  (set_tile "Sblock" (rtos Escb 2 3))
  (set_tile "Old" "1")
  (set_tile "tag2" "1")
  (set_tile "une" "1")
  (set_tile "layer2" "1")
  (set_tile "fecha" fecha)
  (mode_tile "Iniciol" 1)
  (mode_tile "finl" 1)
  (mode_tile "tag1" 1)
  (mode_tile "tag2" 1)
  (mode_tile "Cadena" 1)
  (set_tile "Iniciol" (itoa RI))
  (set_tile "finl" (itoa RF))
  (if (/= dimen "2")
     (set_tile "tres" "1")
     (set_tile "dos" "1")
  )
  (action_tile "examinaf" "(examinaf2)")
  (action_tile "Old2" "(mode_tile_on)")
  (action_tile "Old" "(mode_tile_off)")
  (action_tile "layer1" "(mode_tile_l1)")
;  (action_tile "color" "(leecolor "1")")
  (action_tile "camcolor" "(cambiacolor)")
  (action_tile "layer2" "(mode_tile_l2)")
  (action_tile "tag1" "(st_tile_pr)")
  (action_tile "tag2" "(st_tile_pr)")
  (action_tile "Cadena" "(st_tile_pr)")
  (action_tile "examina" "(examinaf)")
  (action_tile "attrib" "(attributo)")
  (action_tile "accept" "(leevar)")
  (action_tile "cancel" "(exit)")
  (start_dialog)                          ; Display the dialog 
  (done_dialog)
)

(defun convierte ()
   (setq linea1 (comasxspc linea1))
   (setq linea2 (comasxspc linea2))
   (setq linea3 (comasxspc linea3))
   (setq linea4 (comasxspc linea4))
   (setq linea5 (comasxspc linea5))
   (setq linea6 (comasxspc linea6))
   (setq linea7 (comasxspc linea7))
   (setq linea8 (comasxspc linea8))
   (setq linea9 (comasxspc linea9))
   (setq linea10 (comasxspc linea10))
)

(defun comasxspc (vlinea)
  (if (/= vlinea nil)
   (progn
    (setq x (substr vlinea 1 1))
    (setq cont 1)
    (setq vlinea2 "")
    (while (/= x "")
      (if (= x ",") (setq x "    "))
      (setq vlinea2 (strcat vlinea2 x))
      (setq cont (1+ cont))
      (setq x (substr vlinea cont 1))
    )
   )
  )
  (print vlinea2) 
)

(defun atrlist ()
  (setq index (get_tile "atr"))
  (setq index (1+ (atoi index)))
  (setq posa (cdr (assoc index datos2)))
  (setq numerop (cdr (assoc posa datos)))
  (set_tile "posa" (itoa numerop))
)

(defun valposa ()
  (setq index (get_tile "atr"))
  (setq index (1+ (atoi index)))
  (setq posa (cdr (assoc index datos2)))
  (setq numerop (cdr (assoc posa datos)))
  (setq valp (get_tile "posa"))
  (setq valp (atoi valp))
  (setq datos (subst (cons posa valp) (assoc posa datos) datos))
)

(defun camlistbl ()
  (setq nomblox (get_tile "Nblock"))
  (setq nomblo (rblpp (atoi nomblox) (strcat ruta "PROV.TMP")))
  (AtrToList nomblo)
)

(defun tipoarc ()
  (setq index (get_tile "Tpar"))
  (if (= index 0)
    (progn
      (setq datos3 (subst (cons "CODE" 5) (assoc "CODE" datos) datos))
      (setq datos3 (subst (cons "ELEV" 3) (assoc "ELEV" datos) datos))
      (setq datos3 (subst (cons "PUNTO" 4) (assoc "PUNTO" datos) datos))
    )
  )
  (if (= index 1)
    (progn
      (setq datos3 (subst (cons "CODE" 5) (assoc "CODE" datos) datos))
      (setq datos3 (subst (cons "ELEV" 3) (assoc "ELEV" datos) datos))
      (setq datos3 (subst (cons "PUNTO" 4) (assoc "PUNTO" datos) datos))
    )
  )
)

(DEFUN VALIDAFILE ()
  (setq arch (OPEN NOMARCH "r"))
  (setq linea1 (read-line arch))
  (setq linea2 (read-line arch))
  (setq linea3 (read-line arch))
  (close arch)
  (SETQ DATOSL1 (SEPARA_VAL_COMAS LINEA1))
  (SETQ DATOSL2 (SEPARA_VAL_COMAS LINEA2))
  (SETQ DATOSL3 (SEPARA_VAL_COMAS LINEa3))
  (SETQ TPOARCHIVO NIL)
  (SETQ TPOARCHIVO2 NIL)
  (IF (/= (ASSOC 6 DATOSL1) NIL)
    (SETQ TPOARCHIVO 0)                                             ;DELIMITADO POR COMAS CON MAS DE 6 COLUMNAS "0"
  )
  (IF (AND (= (ASSOC 6 DATOSL1) NIL) (/= (ASSOC 5 DATOSL1) NIL))
    (SETQ TPOARCHIVO 1)                                             ;DELIMITADO POR COMAS CON 5 COLUMNAS "1"
  )
  (IF (= TPOARCHIVO NIL)
    (PROGN
      (SETQ DATOSL1 (SEPARA_VAL_SPC LINEA1))
      (SETQ DATOSL2 (SEPARA_VAL_SPC LINEA2))
      (SETQ DATOSL3 (SEPARA_VAL_SPC LINEA3))
      (IF (/= (ASSOC 6 DATOSL1) NIL)
        (SETQ TPOARCHIVO 3)                                             ;DELIMITADO POR ESPACIOS CON MAS DE 6 COLUMNAS "3"
      )
      (IF (AND (= (ASSOC 6 DATOSL1) NIL) (/= (ASSOC 5 DATOSL1) NIL))
        (SETQ TPOARCHIVO 4)                                             ;DELIMITADO POR ESPACIOS CON 5 COLUMNAS "4"
      )
      (IF (= TPOARCHIVO NIL)
        (PROGN
          (SETQ DATOSL1 (SEPARA_VAL_TAB LINEA1))
          (SETQ DATOSL2 (SEPARA_VAL_TAB LINEA2))
          (SETQ DATOSL3 (SEPARA_VAL_TAB LINEA3))
          (IF (/= (ASSOC 6 DATOSL1) NIL)
            (SETQ TPOARCHIVO 5)                                             ;DELIMITADO POR TABULACIONES CON MAS DE 6 COLUMNAS "5"
          )
          (IF (AND (= (ASSOC 6 DATOSL1) NIL) (/= (ASSOC 5 DATOSL1) NIL))
            (SETQ TPOARCHIVO 6)                                             ;DELIMITADO POR TABULACIONES CON 5 COLUMNAS "6"
          )
        )
      )
    )
  )
  (IF (= 0 TPOARCHIVO)
    (progn
      (setq dcl_id (load_dialog (strcat ruta "dialogos\\insatr2.dcl"))) ; Load the DCL file.
      (if (not (new_dialog "mens" dcl_id))   ; Initialize the dialog.
        (exit)                                ; Exit if this doesn't 
                                              ; work.
      )
      (setq width (dimx_tile  "arcsv")
            height (dimy_tile "arcsv"))
      (start_image "arcsv")  
      (slide_image 1 1 width height (STRCAT RUTA "SLIDES\\csv-comas.sld"))
      (end_image)
      (start_dialog)                          ; Display the dialog 
                                              ; box.
      (unload_dialog dcl_id)                  ; Unload the DCL file.
      (princ)
    )
  )
  (IF (= 1 TPOARCHIVO)
    (PROGN
      (SETQ ASOCIAX (CDR (ASSOC 1 DATOSL1)))
      (SETQ TPODATO1 (TIPODATOS ASOCIAX))
      (SETQ ASOCIAX (CDR (ASSOC 2 DATOSL1)))
      (SETQ TPODATO2 (TIPODATOS ASOCIAX))
      (SETQ ASOCIAX (CDR (ASSOC 3 DATOSL1)))
      (SETQ TPODATO3 (TIPODATOS ASOCIAX))
      (SETQ ASOCIAX (CDR (ASSOC 4 DATOSL1)))
      (SETQ TPODATO4 (TIPODATOS ASOCIAX))
      (SETQ ASOCIAX (CDR (ASSOC 5 DATOSL1)))
      (SETQ TPODATO5 (TIPODATOS ASOCIAX))
      (IF (or (AND (= TPODATO1 1) (= TPODATO2 0) (= TPODATO3 0) (= TPODATO4 0) (= TPODATO5 1)) (AND (= TPODATO1 1) (= TPODATO2 1) (= TPODATO3 1) (= TPODATO4 1) (= TPODATO5 2)))
        (progn
          (SETQ ASOCIAX (CDR (ASSOC 1 DATOSL2)))
          (SETQ TPODATO1 (TIPODATOS ASOCIAX))
          (SETQ ASOCIAX (CDR (ASSOC 2 DATOSL2)))
          (SETQ TPODATO2 (TIPODATOS ASOCIAX))
          (SETQ ASOCIAX (CDR (ASSOC 3 DATOSL2)))
          (SETQ TPODATO3 (TIPODATOS ASOCIAX))
          (SETQ ASOCIAX (CDR (ASSOC 4 DATOSL2)))
          (SETQ TPODATO4 (TIPODATOS ASOCIAX))
          (SETQ ASOCIAX (CDR (ASSOC 5 DATOSL2)))
          (SETQ TPODATO5 (TIPODATOS ASOCIAX))
        )
      )
      (IF (or (AND (= TPODATO1 1) (= TPODATO2 0) (= TPODATO3 0) (= TPODATO4 0) (= TPODATO5 1)) (AND (= TPODATO1 1) (= TPODATO2 1) (= TPODATO3 1) (= TPODATO4 1) (= TPODATO5 2)))
        (progn
          (SETQ ASOCIAX (CDR (ASSOC 1 DATOSL3)))
          (SETQ TPODATO1 (TIPODATOS ASOCIAX))
          (SETQ ASOCIAX (CDR (ASSOC 2 DATOSL3)))
          (SETQ TPODATO2 (TIPODATOS ASOCIAX))
          (SETQ ASOCIAX (CDR (ASSOC 3 DATOSL3)))
          (SETQ TPODATO3 (TIPODATOS ASOCIAX))
          (SETQ ASOCIAX (CDR (ASSOC 4 DATOSL3)))
          (SETQ TPODATO4 (TIPODATOS ASOCIAX))
          (SETQ ASOCIAX (CDR (ASSOC 5 DATOSL3)))
          (SETQ TPODATO5 (TIPODATOS ASOCIAX))
        )
      )
      (IF (AND (= TPODATO1 1) (= TPODATO2 0) (= TPODATO3 0) (= TPODATO4 0) (= TPODATO5 2))
        (progn
          (setq dcl_id (load_dialog (strcat ruta "dialogos\\insatr2.dcl"))) ; Load the DCL file.
          (if (not (new_dialog "mens" dcl_id))   ; Initialize the dialog.
            (exit)                                ; Exit if this doesn't 
                                                  ; work.
          )
          (setq width (dimx_tile  "arcsv")
                height (dimy_tile "arcsv"))
          (start_image "arcsv")  
          (slide_image 1 1 width height (STRCAT RUTA "SLIDES\\leica 500.sld"))
          (end_image)
          (start_dialog)                          ; Display the dialog 
                                                  ; box.
          (unload_dialog dcl_id)                  ; Unload the DCL file.
          (princ)
          (ClonaYOrdena2)
        )
      )
      (IF (AND (= TPODATO1 0) (= TPODATO2 0) (= TPODATO3 0) (= TPODATO4 1) (= TPODATO5 2))
        (progn
          (setq dcl_id (load_dialog (strcat ruta "dialogos\\insatr2.dcl"))) ; Load the DCL file.
          (if (not (new_dialog "mens" dcl_id))   ; Initialize the dialog.
            (exit)                                ; Exit if this doesn't 
                                                  ; work.
          )
          (setq width (dimx_tile  "arcsv")
                height (dimy_tile "arcsv"))
          (start_image "arcsv")  
          (slide_image 1 1 width height (STRCAT RUTA "SLIDES\\xyz-insatr.sld"))
          (end_image)
          (start_dialog)                          ; Display the dialog 
                                                  ; box.
          (unload_dialog dcl_id)                  ; Unload the DCL file.
          (princ)
        )
      )
    )
  )
  (IF (= 3 TPOARCHIVO)
    (progn
      (setq dcl_id (load_dialog (strcat ruta "dialogos\\insatr2.dcl"))) ; Load the DCL file.
      (if (not (new_dialog "mens" dcl_id))   ; Initialize the dialog.
        (exit)                                ; Exit if this doesn't 
                                              ; work.
      )
      (setq width (dimx_tile  "arcsv")
            height (dimy_tile "arcsv"))
      (start_image "arcsv")  
      (slide_image 1 1 width height (STRCAT RUTA "SLIDES\\espacios.sld"))
      (end_image)
      (start_dialog)                          ; Display the dialog 
                                              ; box.
      (unload_dialog dcl_id)                  ; Unload the DCL file.
      (princ)
      (ClonaYOrdena3)
    )
  )
  (IF (= 4 TPOARCHIVO)
    (PROGN
      (SETQ ASOCIAX (CDR (ASSOC 1 DATOSL1)))
      (SETQ TPODATO1 (TIPODATOS ASOCIAX))
      (SETQ ASOCIAX (CDR (ASSOC 2 DATOSL1)))
      (SETQ TPODATO2 (TIPODATOS ASOCIAX))
      (SETQ ASOCIAX (CDR (ASSOC 3 DATOSL1)))
      (SETQ TPODATO3 (TIPODATOS ASOCIAX))
      (SETQ ASOCIAX (CDR (ASSOC 4 DATOSL1)))
      (SETQ TPODATO4 (TIPODATOS ASOCIAX))
      (SETQ ASOCIAX (CDR (ASSOC 5 DATOSL1)))
      (SETQ TPODATO5 (TIPODATOS ASOCIAX))
      (IF (AND (= TPODATO1 1) (= TPODATO2 0) (= TPODATO3 0) (= TPODATO4 0) (= TPODATO5 1))
        (progn
          (SETQ ASOCIAX (CDR (ASSOC 1 DATOSL2)))
          (SETQ TPODATO1 (TIPODATOS ASOCIAX))
          (SETQ ASOCIAX (CDR (ASSOC 2 DATOSL2)))
          (SETQ TPODATO2 (TIPODATOS ASOCIAX))
          (SETQ ASOCIAX (CDR (ASSOC 3 DATOSL2)))
          (SETQ TPODATO3 (TIPODATOS ASOCIAX))
          (SETQ ASOCIAX (CDR (ASSOC 4 DATOSL2)))
          (SETQ TPODATO4 (TIPODATOS ASOCIAX))
          (SETQ ASOCIAX (CDR (ASSOC 5 DATOSL2)))
          (SETQ TPODATO5 (TIPODATOS ASOCIAX))
        )
      )
      (IF (AND (= TPODATO1 1) (= TPODATO2 0) (= TPODATO3 0) (= TPODATO4 0) (= TPODATO5 1))
        (progn
          (SETQ ASOCIAX (CDR (ASSOC 1 DATOSL3)))
          (SETQ TPODATO1 (TIPODATOS ASOCIAX))
          (SETQ ASOCIAX (CDR (ASSOC 2 DATOSL3)))
          (SETQ TPODATO2 (TIPODATOS ASOCIAX))
          (SETQ ASOCIAX (CDR (ASSOC 3 DATOSL3)))
          (SETQ TPODATO3 (TIPODATOS ASOCIAX))
          (SETQ ASOCIAX (CDR (ASSOC 4 DATOSL3)))
          (SETQ TPODATO4 (TIPODATOS ASOCIAX))
          (SETQ ASOCIAX (CDR (ASSOC 5 DATOSL3)))
          (SETQ TPODATO5 (TIPODATOS ASOCIAX))
        )
      )
      (IF (AND (= TPODATO1 1) (= TPODATO2 0) (= TPODATO3 0) (= TPODATO4 0) (= TPODATO5 2))
        (progn
          (setq dcl_id (load_dialog (strcat ruta "dialogos\\insatr2.dcl"))) ; Load the DCL file.
          (if (not (new_dialog "mens" dcl_id))   ; Initialize the dialog.
            (exit)                                ; Exit if this doesn't 
                                                  ; work.
          )
          (setq width (dimx_tile  "arcsv")
                height (dimy_tile "arcsv"))
          (start_image "arcsv")  
          (slide_image 1 1 width height (STRCAT RUTA "SLIDES\\leica 407.sld"))
          (end_image)
          (start_dialog)                          ; Display the dialog 
                                                  ; box.
          (unload_dialog dcl_id)                  ; Unload the DCL file.
          (princ)
          (ClonaYOrdena)
        )
      )
    )
  )
  (IF (or (= 5 TPOARCHIVO) (= 6 TPOARCHIVO))
    (progn
      (setq dcl_id (load_dialog (strcat ruta "dialogos\\insatr2.dcl"))) ; Load the DCL file.
      (if (not (new_dialog "mens" dcl_id))   ; Initialize the dialog.
        (exit)                                ; Exit if this doesn't 
                                              ; work.
      )
      (setq width (dimx_tile  "arcsv")
            height (dimy_tile "arcsv"))
      (start_image "arcsv")  
      (slide_image 1 1 width height (STRCAT RUTA "SLIDES\\tabulaciones.sld"))
      (end_image)
      (start_dialog)                          ; Display the dialog 
                                              ; box.
      (unload_dialog dcl_id)                  ; Unload the DCL file.
      (princ)
      (ClonaYOrdena4)
    )
  )
)

(DEFUN TIPODATOS (DATO)
  (SETQ CARX (SUBSTR DATO 1 1))
  (SETQ PUNTERO 1)
  (SETQ TPOCAR nil)
  (WHILE (/= CARX "")
    (IF (AND (OR (AND (> (ASCII CARX) 47) (< (ASCII CARX) 60)) (= (ASCII CARX) 43) (= (ASCII CARX) 45)) (/= TPOCAR 2) (/= TPOCAR 0))
      (SETQ TPOCAR 1)
    )
    (IF (and (or (< (ASCII CARX) 48) (> (ASCII CARX) 59)) (/= (ASCII CARX) 43) (/= (ASCII CARX) 46) (/= (ASCII CARX) 45)) 
      (SETQ TPOCAR 2)
    )
    (if (and (= (ASCII CARX) 46) (/= tpocar 2))
      (SETQ TPOCAR 0)
    )
    (SETQ PUNTERO (1+ PUNTERO))
    (SETQ CARX (SUBSTR DATO PUNTERO 1))
  )
  (PRINT TPOCAR)
)

(defun ClonaYOrdena ()
  (setq arch (OPEN NOMARCH "r"))
  (setq arch2 (OPEN (strcat ruta "csv.tmp") "w"))
  (setq linea1 (read-line arch))
  (while linea1
    (SETQ DATOSL1 (SEPARA_VAL_SPC LINEA1))
    (setq datoscorr (strcat (CDR (ASSOC 2 DATOSL1)) "," (CDR (ASSOC 3 DATOSL1)) "," (rtos (atof (CDR (ASSOC 4 DATOSL1))) 2 3) "," (CDR (ASSOC 1 DATOSL1)) "," (CDR (ASSOC 5 DATOSL1))))
    (write-line datoscorr arch2)
    (setq linea1 (read-line arch))
  )
  (close arch2)
  (close arch)
  (setq nomarch (strcat ruta "csv.tmp"))
)

(defun ClonaYOrdena2 ()
  (setq arch (OPEN NOMARCH "r"))
  (setq arch2 (OPEN (strcat ruta "csv.tmp") "w"))
  (setq linea1 (read-line arch))
  (while linea1
    (SETQ DATOSL1 (SEPARA_VAL_Comas LINEA1))
    (setq datoscorr (strcat (CDR (ASSOC 3 DATOSL1)) "," (CDR (ASSOC 2 DATOSL1)) "," (rtos (atof (CDR (ASSOC 4 DATOSL1))) 2 3) "," (CDR (ASSOC 1 DATOSL1)) "," (CDR (ASSOC 5 DATOSL1))))
    (write-line datoscorr arch2)
    (setq linea1 (read-line arch))
  )
  (close arch2)
  (close arch)
  (setq nomarch (strcat ruta "csv.tmp"))
)

(defun ClonaYOrdena3 ()
  (setq arch (OPEN NOMARCH "r"))
  (setq arch2 (OPEN (strcat ruta "csv.tmp") "w"))
  (setq linea1 (read-line arch))
  (while linea1
    (SETQ DATOSL1 (SEPARA_VAL_SPC LINEA1))
    (setq datoscorr "")
    (setq contAs 1)
    (setq datoAs (CDR (ASSOC contAs DATOSL1)))
    (while datoAs
       (if (= datoscorr "")
         (setq datoscorr (strcat datoscorr datoAs))
         (setq datoscorr (strcat datoscorr "," (CDR (ASSOC 3 DATOSL1))))
       )
       (setq contAs (1+ ContAs))
       (setq datoAs (CDR (ASSOC contAs DATOSL1)))
    )
    (write-line datoscorr arch2)
    (setq linea1 (read-line arch))
  )
  (close arch2)
  (close arch)
  (setq nomarch (strcat ruta "csv.tmp"))
)

(defun ClonaYOrdena4 ()
  (setq arch (OPEN NOMARCH "r"))
  (setq arch2 (OPEN (strcat ruta "csv.tmp") "w"))
  (setq linea1 (read-line arch))
  (while linea1
    (SETQ DATOSL1 (SEPARA_VAL_tab LINEA1))
    (setq datoscorr "")
    (setq contAs 1)
    (setq datoAs (CDR (ASSOC contAs DATOSL1)))
    (while datoAs
       (if (= datoscorr "")
         (setq datoscorr (strcat datoscorr datoAs))
         (setq datoscorr (strcat datoscorr "," (CDR (ASSOC 3 DATOSL1))))
       )
       (setq contAs (1+ ContAs))
       (setq datoAs (CDR (ASSOC contAs DATOSL1)))
    )
    (write-line datoscorr arch2)
    (setq linea1 (read-line arch))
  )
  (close arch2)
  (close arch)
  (setq nomarch (strcat ruta "csv.tmp"))
)

(defun leecolor (color) 
  (setq colorx color)
  (setq color (acad_colordlg (atoi color)))
  (if (= color nil) (setq color colorx) (setq color (itoa color)))
  (setq width (dimx_tile  "color")
        height (dimy_tile "color"))
  (start_image "color")
  (fill_image 0 0 width height (atoi color))
  (end_image)
  (set_tile "color" color)
)
