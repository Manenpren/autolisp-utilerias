(DEFUN c:creareg ()
  (setq arch1 (open (strcat ruta "registro.est") "w"))
  (write-line (dos_acadname) arch1)
  (write-line (dos_cdate "%m/%d/%y") arch1)
  (write-line (dos_hostname) arch1)
  (write-line (dos_username) arch1)
  (write-line (dos_ver) arch1)
  (close arch1)
  (dos_encrypt (strcat ruta "registro.est") "4avEjsD8GlñOpwrpfvc3071fdAGa4TykP8G5Umo9Ye513")
  (setq arch1 (open (strcat ruta "registrod.est") "w"))
  (write-line (dos_cdate "%m/%d/%y") arch1)
  (write-line "0" arch1)
  (write-line "bien" arch1)
  (close arch1)
  (dos_encrypt (strcat ruta "registrod.est") "4avEjsD8GlñOpwrpfvc3071fdAGa4TykP8G5Umo9Ye513")
)
