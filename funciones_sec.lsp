(defun exa ()
     (if (not (new_dialog "SEC2" dcl_id))   ; Initialize the dialog.   2do dialogo
       (exit)                                ; Exit if this doesn't 
                                             ; work.
     )
  (set_tile "sh" shl)
  (set_tile "sv" svl)
  (set_tile "et1" etlh)
  (set_tile "et2" etlv)
  (set_tile "str" stret)
     (action_tile "accept" "(leevr2)")
     (start_dialog)                          ; Display the dialog 
     (if (not (new_dialog "SEC" dcl_id))   ; Initialize the dialog.   2do dialogo
       (exit)                                ; Exit if this doesn't 
                                             ; work.
     )
  (set_TILE "ancho" ancho)
  (set_TILE "scad" escalacad)
  (action_tile "actualiza" "(dibujo)")
  (action_tile "ancho" "(var)")
  (action_tile "scad" "(var2)")
    (action_tile "reticula" "(exa)")
    (action_tile "capas" "(exa2)")
    (action_tile "cfgf" "(exa3)")
    (action_tile "save" "(exa4)")
  (action_tile "colores" "(exa5)")
  (action_tile "accept" "(aceptas)")
     (start_dialog)                          ; Display the dialog 
)

(defun exa2 ()
     (if (not (new_dialog "SEC3" dcl_id))   ; Initialize the dialog.   2do dialogo
       (exit)                                ; Exit if this doesn't 
                                             ; work.
     )
  (set_TILE "ctn" LTN)
  (set_tile "clr" lret)
  (set_tile "ctr" ltret)
  (set_tile "ccad" lcad)
  (set_tile "cniv" lniv)
     (action_tile "accept" "(leevr)")
     (start_dialog)                          ; Display the dialog 
     (if (not (new_dialog "SEC" dcl_id))   ; Initialize the dialog.   2do dialogo
       (exit)                                ; Exit if this doesn't 
                                             ; work.
     )
  (action_tile "actualiza" "(dibujo)")
  (set_TILE "ancho" ancho)
  (set_TILE "scad" escalacad)
  (action_tile "ancho" "(var)")
  (action_tile "scad" "(var2)")
    (action_tile "reticula" "(exa)")
    (action_tile "capas" "(exa2)")
    (action_tile "save" "(exa4)")
  (action_tile "colores" "(exa5)")
    (action_tile "cfgf" "(exa3)")
  (action_tile "accept" "(aceptas)")
     (start_dialog)                          ; Display the dialog 
)

(defun exa3 ()
  (setq NOMARCH (getfiled "ARCHIVO DE DATOS" (strcat ruta "configuraciones de programas\\") "SEC" 32))
  (WHILE (= NOMARCH NIL)
    (setq NOMARCH (getfiled "ARCHIVO DE DATOS" (strcat ruta "configuraciones de programas\\") "SEC" 32))
  )
  (setq arcw (open NOMARCH "r"))
  (setq ANCHO (READ-LINE ARCW))
  (setq escalacad (READ-LINE ARCW))
  (setq LTN (READ-LINE ARCW))
  (setq LRET (READ-LINE ARCW))
  (setq LTRET (READ-LINE ARCW))
  (setq LCAD (READ-LINE ARCW))
  (setq LNIV (READ-LINE ARCW))
  (setq SHL (READ-LINE ARCW))
  (setq SVL (READ-LINE ARCW))
  (setq ETLH (READ-LINE ARCW))
  (setq ETLV (READ-LINE ARCW))
  (setq STRET (READ-LINE ARCW))
  (CLOSE ARCW)
  (SET_TILE "ancho" ancho)
  (SET_TILE "scad" escalacad)
)

(defun exa4 ()
  (setq NOMARCH (getfiled "ARCHIVO DE DATOS" (strcat ruta "configuraciones de programas\\") "SEC" 33))
  (WHILE (= NOMARCH NIL)
    (setq NOMARCH (getfiled "ARCHIVO DE DATOS" (strcat ruta "configuraciones de programas\\") "SEC" 33))
  )
  (setq arcw (open NOMARCH "w"))
  (WRITE-LINE ANCHO ARCW)
  (WRITE-LINE ESCALACAD ARCW)
  (WRITE-LINE LTN ARCW)
  (WRITE-LINE LRET ARCW)
  (WRITE-LINE LTRET ARCW)
  (WRITE-LINE LCAD ARCW)
  (WRITE-LINE LNIV ARCW)
  (WRITE-LINE SHL ARCW)
  (WRITE-LINE SVL ARCW)
  (WRITE-LINE ETLH ARCW)
  (WRITE-LINE ETLV ARCW)
  (WRITE-LINE STRET ARCW)
  (CLOSE ARCW)
)

(defun exa5 ()
     (if (not (new_dialog "SEC4" dcl_id))   ; Initialize the dialog.   2do dialogo
       (exit)                                ; Exit if this doesn't 
                                             ; work.
     )
  (set_TILE "color1" cTN)
  (set_tile "color2" cret)
  (set_tile "color3" ctret)
  (set_tile "color4" ccad)
  (set_tile "color5" cniv)

  (setq width (dimx_tile  "fcolor1")
        height (dimy_tile "fcolor1"))
  (start_image "fcolor1")
  (fill_image 0 0 width height (atoi ctn))   
  (end_image)
  (setq width (dimx_tile  "fcolor2")
        height (dimy_tile "fcolor2"))
  (start_image "fcolor2")
  (fill_image 0 0 width height (atoi cret))   
  (end_image)
  (setq width (dimx_tile  "fcolor3")
        height (dimy_tile "fcolor3"))
  (start_image "fcolor3")
  (fill_image 0 0 width height (atoi ctret))   
  (end_image)
  (setq width (dimx_tile  "fcolor4")
        height (dimy_tile "fcolor4"))
  (start_image "fcolor4")
  (fill_image 0 0 width height (atoi ccad))   
  (end_image)
  (setq width (dimx_tile  "fcolor5")
        height (dimy_tile "fcolor5"))
  (start_image "fcolor5")
  (fill_image 0 0 width height (atoi cniv))   
  (end_image)

  (action_tile "fcolor1" "(colores1)")
  (action_tile "fcolor2" "(colores2)")
  (action_tile "fcolor3" "(colores3)")
  (action_tile "fcolor4" "(colores4)")
  (action_tile "fcolor5" "(colores5)")
     (action_tile "accept" "(leevr3)")
     (start_dialog)                          ; Display the dialog 
     (if (not (new_dialog "SEC" dcl_id))   ; Initialize the dialog.   2do dialogo
       (exit)                                ; Exit if this doesn't 
                                             ; work.
     )
  (set_TILE "ancho" ancho)
  (set_TILE "scad" escalacad)
  (action_tile "actualiza" "(dibujo)")
  (action_tile "ancho" "(var)")
  (action_tile "scad" "(var2)")
    (action_tile "reticula" "(exa)")
    (action_tile "capas" "(exa2)")
    (action_tile "cfgf" "(exa3)")
    (action_tile "save" "(exa4)")
  (action_tile "colores" "(exa5)")
  (action_tile "accept" "(aceptas)")
     (start_dialog)                          ; Display the dialog 
)

(defun leevr ()
  (setq ltn (get_tile "ctn"))
  (setq lret (get_tile "clr"))
  (setq ltret (get_tile "ctr"))
  (setq lcad (get_tile "ccad"))
  (setq lniv (get_tile "cniv"))
  (done_dialog)
)

(defun leevr2 ()
  (setq shl (get_tile "sh"))
  (setq svl (get_tile "sv"))
  (setq EtLh (get_tile "et1"))
  (setq EtLv (get_tile "et2"))
  (setq stret (get_tile "str"))
  (done_dialog)
)

(defun leevr3 ()
  (setq ctn (get_tile "color1"))
  (setq cret (get_tile "color2"))
  (setq ctret (get_tile "color3"))
  (setq ccad (get_tile "color4"))
  (setq cniv (get_tile "color5"))
  (done_dialog)
)

(defun var ()
  (setq ancho (get_tile "ancho"))
)

(defun var2 ()
  (setq escalacad (get_tile "scad"))
)

(defun var23 ()
  (setq opescaneo (get_tile "escan"))
)

(defun var3 ()
  (setq altura (get_tile "altura"))
  (setq sver (get_tile "sver"))
  (setq shor (get_tile "shor"))
)

(defun aceptas ()
  (setq ArcCon (open (strcat ruta "configuraciones de programas\\ConfiSec.txt") "w"))
  (write-line (strcat "Ancho total de Sección: " ancho) ArcCon)
  (write-line (strcat "Separación Hor. de Líneas: " SHL) ArcCon)
  (write-line (strcat "Separación Hor. de Textos: " ETLH) ArcCon)
  (write-line (strcat "Separación Ver. de líneas: " SVL) ArcCon)
  (write-line (strcat "Separación Ver. de Textos: " ETLV) ArcCon)
  (write-line (strcat "Archivo a descargar datos: " "C:\\PERFX.LSP") ArcCon)
  (write-line (strcat "Terreno Natural: " LTN) ArcCon)
  (write-line (strcat "Lineas de retícula en: " LRET) ArcCon)
  (write-line (strcat "Textos de retícula en: " LTRET) ArcCon)
  (write-line (strcat "Cadenamiento en: " LCAD) ArcCon)
  (write-line (strcat "Cota en: " LNIV) ArcCon)
  (write-line (strcat "Escala textos cad: " escalacad) ArcCon)
  (write-line (strcat "Escala textos ret: " stret) ArcCon)
  (close ArcCon)
  (C:RESE)
  (done_dialog)
)

(defun dibujo ()
 (setq width (dimx_tile  "imagen")
       height (dimy_tile "imagen"))
 (start_image "imagen")
 (fill_image 0 0 width height 0)   ;1 = AutoCAD red.
 (setq imancho (/ 520 (atof ancho)))
 (vector_image 40 180 560 180 (atoi cret))  
 (setq imy2 (fix (- 180 (* (atof shl) imancho))))
 (vector_image 40 imy2 560 imy2 (atoi cret))  
 (setq imy3 (fix (- 180 (* (* (atof shl) imancho) 2))))
 (vector_image 40 imy3 560 imy3 (atoi cret))  
 (setq imy4 (fix (- 180 (* (* (atof shl) imancho) 3))))
 (vector_image 40 imy4 560 imy4 (atoi cret))  
 (setq imy5 (fix (- 180 (* (* (atof shl) imancho) 4))))
 (vector_image 40 imy5 560 imy5 (atoi cret))  
 (vector_image 40 180 40 imy5 (atoi cret))  
 (vector_image 560 180 560 imy5 (atoi cret))  
 (setq imancho2 (/ (atof ancho) (atof svl)))
 (setq imancho3 (* imancho (atof svl)))
; (slide_image 40 180 520 20 (STRCAT RUTA "SLIDES\\ltn.SLD"))
 (setq cont 1)
 (repeat (fix (1- imancho2))
   (setq imx (fix (+ 40 (* imancho3 cont))))
   (vector_image imx 180 imx imy5 (atoi cret))  
   (setq cont (1+ cont))
 )
 (setq imst (* (* imancho (atof stret)) 3.5))
 (setq imst2 (* (* imancho (atof ESCALACAD)) 3))
 (setq x1 (fix (* imst 2)))
 (setq y1 (fix (- 180 (/ imst 2))))
 (setq y2 (fix (* imst 1.1)))
 (setq x2 (fix (- x1 20)))
 (SETQ XI (FIX (+ (* X2 -1) 30)))
 (slide_image XI y1 (FIX (* IMST 6)) (FIX IMST) (STRCAT RUTA "SLIDES\\TEXTO.SLD"))
 (slide_image XI (FIX (- IMY2 (/ imst 2))) (FIX (* IMST 6)) (FIX IMST) (STRCAT RUTA "SLIDES\\TEXTO.SLD"))
 (slide_image XI (FIX (- IMY3 (/ imst 2))) (FIX (* IMST 6)) (FIX IMST) (STRCAT RUTA "SLIDES\\TEXTO.SLD"))
 (slide_image XI (FIX (- IMY4 (/ imst 2))) (FIX (* IMST 6)) (FIX IMST) (STRCAT RUTA "SLIDES\\TEXTO.SLD"))
 (slide_image XI (FIX (- IMY5 (/ imst 2))) (FIX (* IMST 6)) (FIX IMST) (STRCAT RUTA "SLIDES\\TEXTO.SLD"))
 (SETQ XI2 (FIX (+ 560 (* IMST 0.2))))
 (slide_image XI2 y1 (FIX (* IMST 6)) (FIX IMST) (STRCAT RUTA "SLIDES\\TEXTO.SLD"))
 (slide_image XI2 (FIX (- IMY2 (/ imst 2))) (FIX (* IMST 6)) (FIX IMST) (STRCAT RUTA "SLIDES\\TEXTO.SLD"))
 (slide_image XI2 (FIX (- IMY3 (/ imst 2))) (FIX (* IMST 6)) (FIX IMST) (STRCAT RUTA "SLIDES\\TEXTO.SLD"))
 (slide_image XI2 (FIX (- IMY4 (/ imst 2))) (FIX (* IMST 6)) (FIX IMST) (STRCAT RUTA "SLIDES\\TEXTO.SLD"))
 (slide_image XI2 (FIX (- IMY5 (/ imst 2))) (FIX (* IMST 6)) (FIX IMST) (STRCAT RUTA "SLIDES\\TEXTO.SLD"))
 (setq cont 1)
 (repeat (fix (1- imancho2))
   (setq imx (fix (- (+ 40 (* imancho3 cont)) (* IMST 0.70))))
   (IF (= CONT (/ (fix imancho2) 2))
    (PROGN
      (slide_image IMX IMY3 (FIX (* IMST2 6)) (FIX IMST2) (STRCAT RUTA "SLIDES\\CADENA.SLD"))
      (slide_image IMX IMY5 (FIX (* IMST2 6)) (FIX IMST2) (STRCAT RUTA "SLIDES\\ELEV.SLD"))
    )
   )
   (slide_image IMX 180 (FIX (* IMST 6)) (FIX IMST) (STRCAT RUTA "SLIDES\\TEXTO2.SLD"))
   (setq cont (1+ cont))
 )
 (end_image)
)

(defun colores1 ()
  (setq ctn (itoa (acad_colordlg (atoi ctn))))
  (setq width (dimx_tile  "fcolor1")
        height (dimy_tile "fcolor1"))
  (start_image "fcolor1")
  (fill_image 0 0 width height (atoi ctn))   
  (end_image)
  (set_tile "color1" ctn)
)

(defun colores2 ()
  (setq cret (itoa (acad_colordlg (atoi cret))))
  (setq width (dimx_tile  "fcolor2")
        height (dimy_tile "fcolor2"))
  (start_image "fcolor2")
  (fill_image 0 0 width height (atoi cret))   
  (end_image)
  (set_tile "color2" cret)
)

(defun colores3 ()
  (setq ctret (itoa (acad_colordlg (atoi ctret))))
  (setq width (dimx_tile  "fcolor3")
        height (dimy_tile "fcolor3"))
  (start_image "fcolor3")
  (fill_image 0 0 width height (atoi ctret))   
  (end_image)
  (set_tile "color3" ctret)
)

(defun colores4 ()
  (setq ccad (itoa (acad_colordlg (atoi ccad))))
  (setq width (dimx_tile  "fcolor4")
        height (dimy_tile "fcolor4"))
  (start_image "fcolor4")
  (fill_image 0 0 width height (atoi ccad))   
  (end_image)
  (set_tile "color4" ccad)
)

(defun colores5 ()
  (setq cniv (itoa (acad_colordlg (atoi cniv))))
  (setq width (dimx_tile  "fcolor5")
        height (dimy_tile "fcolor5"))
  (start_image "fcolor5")
  (fill_image 0 0 width height (atoi cniv))   
  (end_image)
  (set_tile "color5" cniv)
)

(defun dibujo2 ()
 (setq width (dimx_tile  "imagen")
       height (dimy_tile "imagen"))
 (start_image "imagen") ;431, 260
 (setq imancho (/ 431 (atof ALTURA)))
; (slide_image XI2 y1 (FIX (* IMST 6)) (FIX IMST) (STRCAT RUTA "SLIDES\\TEXTO.SLD"))
; (slide_image XI2 (FIX (- IMY2 (/ imst 2))) (FIX (* IMST 6)) (FIX IMST) (STRCAT RUTA "SLIDES\\TEXTO.SLD"))
; (slide_image XI2 (FIX (- IMY3 (/ imst 2))) (FIX (* IMST 6)) (FIX IMST) (STRCAT RUTA "SLIDES\\TEXTO.SLD"))
; (slide_image XI2 (FIX (- IMY4 (/ imst 2))) (FIX (* IMST 6)) (FIX IMST) (STRCAT RUTA "SLIDES\\TEXTO.SLD"))
; (slide_image XI2 (FIX (- IMY5 (/ imst 2))) (FIX (* IMST 6)) (FIX IMST) (STRCAT RUTA "SLIDES\\TEXTO.SLD"))
 (end_image)
)
