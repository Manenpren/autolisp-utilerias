(defun C:extrae ()
   (setq gpox (ssadd))
   (setq gpox (ssget '((0 . "CIRCLE"))))
   (setq cont 0)
   (SETQ ARCH (OPEN "c:\EXTRAE.CSV" "w"))
   (setq e (ssname gpox cont))
   (while e
      (SETQ X (car (cdr (assoc 10 (ENTGET E)))))
      (SETQ Y (cadr (cdr (assoc 10 (ENTGET E)))))
      (SETQ Z (caddr (cdr (assoc 10 (ENTGET E)))))
      (SETQ LIN (STRCAT (RTOS X 2 3) "," (RTOS Y 2 3) "," (RTOS Z 2 3)))
      (WRITE-LINE LIN ARCH)
      (SETQ CONT (1+ CONT))
      (setq e (ssname gpox cont))
   )
   (CLOSE ARCH)
)
