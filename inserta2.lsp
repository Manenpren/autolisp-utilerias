(defun c:is ()
    (setq texto (car (entsel "Selecciona la cota: ")))
    (setq NOMBLO (cdr (assoc 1 (entget TEXTO))))
    (setq elev2 (car (entsel "Selecciona el texto de tn : ")))
    (setq elev (car (entsel "Selecciona el texto de proyecto : ")))
    (setq n2 (cdr (assoc 1 (entget elev))))
    (setq n3 (cdr (assoc 1 (entget elev2))))
    (setq xy (strcat "0, " n2))
    (command "insert" (STRCAT "*" nomblo) "0,0" "" "" "")
    (COMMAND "ZOOM" "C" XY "60")
    (COMMAND "EXPLODE" L "")
    (COMMAND "INSERT" "L" XY "" "" "")
    (SETQ OP (GETSTRING "CORTE O TERRAPLEN C/T :"))
    (IF (= OP "C")
      (SETQ BLOCK "CORTE")
      (SETQ BLOCK "TERRAP")
    )
    (COMMAND "ERASE" "L" "")
    (command "insert" BLOCK xy "" "" "")
    (command "CHANGE" texto elev "" "P" "C" "RED" "")
    (COMMAND "-LAYER" "F" "RETICULA" "")
)
