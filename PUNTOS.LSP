; PUNTOS.LSP
; ESTE PROGRAMA ESTA DISE¥ADO PARA QUE MEDIANTE UNA BASE DE DATOS CON
; VALORES SEPARADOS POR "COMAS"; CREE UN DIBUJO EN DOS DIMENSIONES CON LOS
; VALORES "X", "Y", NUMERO DE PUNTO Y CODIGO EL VALOR "Z" NO ES TOMADO
; EN CUENTA

;  **********EJEMPLO DEL ORDEN DE LA BASE DE DATOS**********

; ³  X    ³   Y   ³    Z    ³   NUM. PUNTO  ³   CODIGO    ³
; ³ 100.00³ 100.00³ 100.00  ³           1   ³    BANQ     ³

   ;  Û²±°   COMANDO   °±²Û
;  ³ PUNTOS = INSERTAR PUNTOS ³

(DEFUN SUMA (P VX VY)
  (SETQ X (CAR P))
  (SETQ Y (CAR (CDR P)))
  (LIST (+ X VX) (+ Y VY) (LAST P))
)

(defun equis ()
  (if (< xmayor (atof dat))
    (setq xmayor (atof dat))
  )
  (if (> xmenor (atof dat))
    (setq xmenor (atof dat))
  )
)

(defun ye ()
  (if (< ymayor (atof dat))
    (setq ymayor (atof dat))
  )
  (if (> ymenor (atof dat))
    (setq ymenor (atof dat))
  )
)

(DEFUN COLUMNAS ()
  (print l)
  (SETQ CA (SUBSTR LIN 1 1))
  (SETQ C 0) (SETQ X 1)
  (setq xmayor 0) (setq xmenor 0) (setq ymayor 0) (setq ymenor 0)
  (WHILE (/= C 3)
    (SETQ C (+ C 1))
    (SETQ DAT "")
    (WHILE (/= CA ",")
      (SETQ X (+ X 1))
      (SETQ DAT (STRCAT DAT CA))
      (SETQ CA (SUBSTR LIN X 1))
    )
    (SETQ CA "")
    (if (= c 1)
      (equis)
    )
    (if (= c 2)
      (ye)
    )
  )
)

(DEFUN LEEPUN ()
  (SETQ LIN (READ-LINE arch))
  (SETQ L 1)
  (LEEINI)
  (WHILE (AND LIN (<= L FIN))
    (COLUMNAS)
    (SETQ L (+ L 1))
    (SETQ LIN (READ-LINE arch))
  )
  (SETQ L (- L 1))
)

(DEFUN UNE ()
  (command "LAYER" "S" "LINEAS" "")
  (COMMAND "PLINE" P PA "")
  (SETQ ULLI (ENTLAST))
  (setq paso 1)
  (command "LAYER" "S" "0" "")
)

(DEFUN UNESEG ()
  (if (= paso 1)
    (COMMAND "PEDIT" ULLI "J" "ALL" "" "")
  )
)

(DEFUN COLUMNAS2 ()
  (SETQ CA (SUBSTR LIN 1 1))
  (SETQ C 0) (SETQ X 1)
  (SETQ ATRIBUTOS NIL)
  (WHILE (/= C 5)
    (SETQ C (+ C 1))
    (SETQ DAT "")
    (SETQ SALIR "N")
    (WHILE SALIR
      (SETQ X (+ X 1))
      (SETQ DAT (STRCAT DAT CA))
      (SETQ CA (SUBSTR LIN X 1))
      (IF (= CA ",")
        (SETQ SALIR nil)
      )
      (IF (= CA "")
        (SETQ SALIR nil)
      )
    )
    (SETQ CA "")
    (setq atributo (cons c dat))
    (setq atributos (append atributos (list atributo)))
  )
  (IF (= "3" TRI)
    (COMMAND "INSERT" (STRCAT RUTA "BLOCKS\\PUNTO") (LIST (ATOF (CDR (ASSOC 1 ATRIBUTOS)))
                                    (ATOF (CDR (ASSOC 2 ATRIBUTOS)))
                                    (ATOF (CDR (ASSOC 3 ATRIBUTOS)))
                              )
                              TT "" "" (CDR (ASSOC 4 ATRIBUTOS))
                                       (CDR (ASSOC 5 ATRIBUTOS))
    )
    (COMMAND "INSERT" (STRCAT RUTA "BLOCKS\\PUNTO") (LIST (ATOF (CDR (ASSOC 1 ATRIBUTOS)))
                                    (ATOF (CDR (ASSOC 2 ATRIBUTOS)))
                              )        
                              TT "" "" (CDR (ASSOC 4 ATRIBUTOS))
                                       (CDR (ASSOC 5 ATRIBUTOS))
    )
  )
  (SETQ PA P)
  (IF (= "3" TRI)
    (SETQ P (LIST (ATOF (CDR (ASSOC 1 ATRIBUTOS)))
                   (ATOF (CDR (ASSOC 2 ATRIBUTOS)))
                   (ATOF (CDR (ASSOC 3 ATRIBUTOS)))
             )
    )
    (SETQ P (LIST (ATOF (CDR (ASSOC 1 ATRIBUTOS)))
                   (ATOF (CDR (ASSOC 2 ATRIBUTOS)))
             )
    )
  )
  (SETQ CODIGOA CODIGO)
  (SETQ CODIGO (CDR (ASSOC 5 ATRIBUTOS)))
 (if (/= oldop "todo")
  (IF (/= L INI)
    (IF (= CODIGO CODIGOA)
      (UNE)
      (UNESEG)
    )
  )
  (IF (= CODIGO CODIGOA)
    (UNE)
    (UNESEG)
  )
 )
)

(DEFUN LEEINI ()
 (if (/= oldop "todo")
  (WHILE (/= L INI)
    (SETQ L (+ L 1))
    (SETQ LIN (READ-LINE arch))
  )
  (SETQ LIN (READ-LINE arch))
 )
)

(DEFUN LEE2PUN ()
  (SETQ LIN (READ-LINE arch))
  (SETQ L 1) (setq atributos nil)
  (LEEINI)
  (if (/= oldop "todo")
    (WHILE (AND LIN (<= L FIN))
      (COLUMNAS2)
      (SETQ L (+ L 1))
      (SETQ LIN (READ-LINE arch))
    )
    (WHILE LIN 
      (COLUMNAS2)
      (SETQ LIN (READ-LINE arch))
    )
  )
  (SETQ L (- L 1))
)

(defun continua ()
    (C:LIBRERIA "busca block en base de datos")
    (SETQ OPCIONESOS (GETVAR "OSMODE"))
    (command "undo" "m")
    (command "osnap" "none")
    (SETQ VALIDA (SBLBD "PUNTO"))
    (IF (/= "S" VALIDA) (SETQ VALIDA (SBLBD "punto")))
    (If (/= VALIDA "S") 
      (PROGN 
       (COMMAND "INSERT" (STRCAT RUTA "BLOCKS\\PUNTO.dwg") "0,0" "" "" "" "" "" "" "")
       (COMMAND "ERASE" (ENTLAST) "")
      )
    )
  (setq ARCPUN (OPEN (strcat ruta "configuraciones de programas\\PUNTOS.CFG") "r"))
  (IF (= ARCPUN NIL)
   (PROGN
    (SETQ ESCB 1.00)
    (SETQ ARCHIVOP "c:\\TOPOGRAF\\PROV.CSV")
    (SETQ RI 1)
    (SETQ RF 100)
    (SETQ DIMEN "2")
   )
   (PROGN
    (setq ESCB (read-line ARCPUN))
    (if (/= escb nil)
      (SETQ ESCB (ATOF ESCB))
      (SETQ ESCB 1.0)
    )
    (setq ARCHIVOP (read-line ARCPUN))
    (setq RI (read-line ARCPUN))
    (if (/= ri nil)
      (SETQ RI (ATOI RI))
      (SETQ RI 1)
    )
    (setq RF (read-line ARCPUN))
    (if (/= rf nil)
      (SETQ Rf (ATOI Rf))
      (SETQ Rf 1000)
    )
    (setq DIMEN (read-line ARCPUN))
    (IF (= archivop NIL) (SETQ archivop "c:\\topograf\\prov.csv"))
    (IF (= dimen NIL) (SETQ dimen "2"))
    (CLOSE ARCPUN)
   )
  )
    (setq TT ESCB)
  (command "LAYER" "M" "LINEAS" "C" "3" "LINEAS" "")
  (command "LAYER" "S" "0" "")
  (setq paso 0)
  (SETQ PROVS (RTOS ESCB))
  (setq NOMARCH (getfiled "ARCHIVO DE DATOS" ARCHIVOP "CSV" 32))
  (WHILE (= NOMARCH NIL)
    (setq NOMARCH (getfiled "SELECCIONA EL ARCHIVO DE DATOS" ARCHIVOP "CSV" 32))
  )
  (setq dcl_id (load_dialog (strcat ruta "dialogos\\puntos.dcl"))) ; Load the DCL file.
  (if (not (new_dialog "puntos" dcl_id))   ; Initialize the dialog.
    (exit)                                ; Exit if this doesn't 
                                          ; work.
  )
  (set_tile "Arcf" nomarch)
  (set_tile "Sblock" (rtos Escb 2 3))
  (set_tile "Old" "1")
  (set_tile "Iniciol" (itoa RI))
  (mode_tile "Iniciol" 1)
  (mode_tile "finl" 1)
  (set_tile "finl" (itoa RF))
  (if (/= dimen "2")
     (set_tile "tres" "1")
     (set_tile "dos" "1")
  )
  (action_tile "Old2" "(mode_tile_on)")
  (action_tile "Old" "(mode_tile_off)")
  (action_tile "examinaf" "(examinaf2)")
  (action_tile "accept" "(leevar)")
  (action_tile "cancel" "(exit)")
  (start_dialog)                          ; Display the dialog 
                                          ; box.
  (unload_dialog dcl_id)                  ; Unload the DCL file.
  (princ)
  (setq TT ESCB)
  (IF (/= resultado8 "1")
    (setq TRI "3")
    (setq TRI "2")
  )
  (IF (= resultado4 "1")
    (setq oldop "todo")
    (setq oldop "bloque")
  )
  (setq arch (OPEN NOMARCH "r"))
  (if arch
    (LEEPUN)
    (print "\n Archivo no encontrado ")
  )
  (setq ARCPUN (OPEN (strcat ruta "configuraciones de programas\\PUNTOS.CFG") "w"))
  (WRITE-LINE (RTOS tt 2 3) ARCPUN)
  (WRITE-LINE NOMARCH ARCPUN)
  (WRITE-LINE (RTOS INI 2 3) ARCPUN)
  (WRITE-LINE (RTOS FIN 2 3) ARCPUN)
  (WRITE-LINE DIMEN ARCPUN)
  (CLOSE ARCPUN)
  (close arch)
  (setq arch (OPEN NOMARCH "r"))
  (if arch
    (LEE2PUN)
  )
  (UNESEG)
  (close arch)
  (SETVAR "OSMODE" OPCIONESOS)
  (command "ZOOM" "E")
)

(defun c:punts ()
  (continua)
)

(defun examinaf2 ()
  (setq NOMARCH2 (getfiled "Archivo Fuente" ARCHIVOP "CSV" 32))
  (WHILE (= NOMARCH2 NIL)
    (setq NOMARCH2 (getfiled "SELECCIONA EL ARCHIVO DE DATOS" ARCHIVOP "CSV" 32))
  )
  (setq NOMARCh NOMARCH2)
  (set_tile "Arcf" Nomarch)
)

(defun leevar ()
  (setq nomarch (get_tile "Arcf"))
  (setq escb (atof (get_tile "Sblock")))
  (setq resultado4 (get_tile "Old"))
  (setq ini (get_tile "Iniciol"))
  (setq ini (atoi ini))
  (setq fin (get_tile "finl"))
  (setq fin (atoi fin))
  (setq resultado8 (get_tile "dos"))
  (done_dialog)
)

(defun mode_tile_on()
  (mode_tile "Iniciol" 0)
  (mode_tile "finl" 0)
)

(defun mode_tile_off()
  (mode_tile "Iniciol" 1)
  (mode_tile "finl" 1)
)
