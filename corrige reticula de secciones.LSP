(DEFUN C:seca ()
  (COMMAND "UNDO" "M")
  (COMMAND "VIEW" "S" "C")
  (C:LIBRERIA "busca block en base de datos")
  (C:LIBRERIA "ZOOM ULTIMO OBJETO INSERTADO")
  (C:LIBRERIA "VERTICES DE UNA LWPOLYLINE")
  (COMMAND "LUNITS" 2)
  (COMMAND "LUPREC" 7)
  (COMMAND "AUNITS" 0)
  (COMMAND "AUPREC" 4)
  (COMMAND "ANGDIR" 0)
  (COMMAND "ANGBASE" 0.0)
  (COMMAND "DIMZIN" 0)
  (prompt "selecciona el grupo de bloques a extraer")
  (setq gpodse (ssget))
  (setq cont2 0)
  (setq block 1)
  (while block
   (setq BLOCK (ssname gpodse cont2))
   (if (/= block nil)
     (progn
       (setq cont2 (1+ cont2))
       (setq NOMBLO (cdr (assoc 2 (entget BLOCK))))
       (setq nb2 nomblo)
       (COMMAND "INSERT" NOMBLO "0,0" "" "" "")
       (SETQ X (ENTLAST))
       (ZBLOCK)
       (setq gpot (SSGET "P"))
       (SETQ POLY (SSGET "P" '((0 . "LWPOLYLINE"))))
       (IF (/= (sslength POLY) 1)
         (PROGN 
           (ALERT "la seccion no tiene polylinea o tiene dos segmentos de ella,corregir y reiniciar programa")
           (exit)
         )
       )
       (setq linea1 (car (entsel "Selecciona la linea izquierda : ")))
       (setq linea2 (car (entsel "Selecciona la linea a tomar distancia abajo: ")))
       (setq vert1 (cdr (assoc 10 (entget linea2))))
       (SETQ XV (CAR vert1))
       (SETQ yV (CAdR vert1))
       (setq vert2 (cdr (assoc 11 (entget linea2))))
       (SETQ XV2 (CAR vert2))
       (SETQ yV2 (CAdR vert2))
       (setq distancia (+ (abs xv) (abs xv2)))
       (command "array" linea1 "" "R" "1" (fix distancia) "1")
;       (if (> 1 (- ymax ymin))
;          (progn
;          (ALERT "la seccion tiene un desnivel menor de 1 metros revisar si esta correcta")
;           (close f1)
;           (exit)
;         )
;       )
       (setq gpop (ssget))
       (command "BLOCK" nomblo "Y" "0,0" gpot gpop "")
     )  			;progn
   )  			;if
  )         		; while
  (COMMAND "VIEW" "r" "C")
)
