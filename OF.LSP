(defun C:OF ()
  (COMMAND "UNDO" "M")
  (COMMAND "VIEW" "S" "CAMCOL")
  (setq PROV (CAR (ENTSEL "SELECCIONA BLOCK")))
  (setq NOMBLO (cdr (assoc 2 (entget PROV))))
  (COMMAND "INSERT" NOMBLO "0,0" "" "" "")
  (SETQ X (ENTLAST))
  (COMMAND "EXPLODE" X "")
  (SETQ GPOA (SSGET "P"))
  (SETQ P 0)
  (WHILE (/= (cdr (assoc 0 (entget PROV))) "TEXT")
    (SETQ PROV (SSNAME GPOA P))
    (SETQ P (1+ P))
  )
  (setq XY (cdr (assoc 10 (entget PROV))))
  (COMMAND "ZOOM" "C" XY "10")
  (SETQ TN (CAR (ENTSEL "SELECCIONA LINEA DE TERRENO NATURAL")))
  (COMMAND "ZOOM" "C" XY "30")
  (COMMAND "PEDIT" TN "" "J" GPOA "" "")
  (SSADD (ENTLAST) GPOA)
  (SETQ X (ENTLAST))
  (COMMAND "OFFSET" ".6" X XY "0,0" "")
  (SSADD (ENTLAST) GPOA)
  (COMMAND "CHANGE" X "" "P" "C" "GREEN" "")
   (COMMAND "BLOCK" NOMBLO "Y" "0,0" GPOA "")
   (COMMAND "VIEW" "R" "CAMCOL")
)
