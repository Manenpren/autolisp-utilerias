(defun c:CAML ()
        (setq e (car (entsel "Selecciona el objeto a cambear de layer: ")))
        (setq ob (cdr (assoc 0 (entget e))))
        (if (= "LINE" OB)
            (SETQ OP 1)
        )
        (if (= "INSERT" OB)
          (PROGN
            (setq NOMBRE (cdr (assoc 2 (entget e))))
            (setq escala (cdr (assoc 41 (entget e))))
            (SETQ OP 2)
          )
        )
        (if (= "TEXT" OB)
          (PROGN
            (setq escala (cdr (assoc 40 (entget e))))
            (SETQ OP 3)
          )
        )
        (if (= "MTEXT" OB)
          (PROGN
            (setq escala (cdr (assoc 40 (entget e))))
            (SETQ OP 4)
          )
        )
        (if (= "LWPOLYLINE" OB)
          (PROGN
            (SETQ OP 5)
          )
        )
        (setq NEWLAY (getstring "\n NUEVO LAYER: "))
        (COMMAND "CHANGE")
        (setq E (entnext))
        (while E
         (SETQ OB (entget e))
         (SETQ TIP (cdr (assoc 0 OB)))
         (IF (= OP 1)
            (IF (= "LINE" TIP)
                (COMMAND E)
            )
         )
         (IF (= OP 2)  
            (IF (= "INSERT" TIP)
              (PROGN
                (setq NOMBRE2 (cdr (assoc 2 OB)))
                (setq escala2 (cdr (assoc 41 OB)))
                (IF (= ESCALA ESCALA2)
                    (IF (= NOMBRE NOMBRE2)
                        (COMMAND E)
                    )
                )
              )
            )
         )
         (IF (= OP 3)  
            (IF (= "TEXT" TIP)
              (PROGN
                (setq escala2 (cdr (assoc 40 OB)))
                (IF (= ESCALA ESCALA2)
                    (COMMAND E)
                )
              )
            )
         )
         (IF (= OP 4)  
            (IF (= "MTEXT" TIP)
              (PROGN
                (setq escala2 (cdr (assoc 40 OB)))
                (IF (= ESCALA ESCALA2)
                    (COMMAND E)
                )
              )
            )
         )
         (IF (= OP 5)  
            (IF (= "LWPOLYLINE" TIP)
                (COMMAND E)
            )
         )
         (setq E (entnext E))
        )
        (COMMAND "" "P" "LA" NEWLAY "")
)
