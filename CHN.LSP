(defun C:CHN2(/ obj p1 e1 sp ep ang p2 p0)
  (setvar "cmdecho" 0)
  (command "ucs" "w")
  (setq obj (entsel))
  (if (and (/= obj nil) (= (cdr (assoc 0 (entget
(car obj)))) "LINE"))
    (progn
      (setq p1 (cadr obj)
             e1 (entget (car obj))
         sp (cdr (assoc 10 e1))
         ep (cdr (assoc 11 e1))
             ang (angle sp ep)
       )
       (initget 1 "D")
      (setq p2 (getpoint
"\nDistance<Change point> : "))
       (if  (Listp p2)
         (setq p0 (inters sp ep p2 (polar p2 (+ ang (/
pi 2)) 10) nil))
        (progn
         (initget 1)
            (setq p2 (getdist "\nEnter Distance : "))
        (if (< (distance sp p1) (distance ep p1))
              (setq p0 (polar sp (+ ang pi) p2))
              (setq p0 (polar ep ang p2))
            )
        )
      )
     (if (< (distance sp p1) (distance ep p1))
       (progn (setq e1 (subst (cons 10 p0)
(assoc 10 e1) e1))
           (entmod e1))
        (progn (setq e1 (subst (cons 11 p0)
(assoc 11 e1) e1))
           (entmod e1))
      )
    )
    (princ "\n* Please select Line entity! *\n")
  )
  (command "ucs" "p") (setvar "cmdecho" 1) (prin1)
)
