(defun C:AREAS()
  (COMMAND "VIEW" "S" "CAMCOL")
  (setq PROV (CAR (ENTSEL "SELECCIONA BLOCK")))
  (setq NOMBLO (cdr (assoc 2 (entget PROV))))
  (COMMAND "INSERT" NOMBLO "0,0" "" "" "")
  (SETQ X (ENTLAST))
  (COMMAND "EXPLODE" X "")
  (SETQ GPOA (SSGET "P"))
  (SETQ P 0)
  (WHILE (/= (cdr (assoc 0 (entget PROV))) "TEXT")
    (SETQ PROV (SSNAME GPOA P))
    (SETQ P (1+ P))
  )
  (setq XY (cdr (assoc 10 (entget PROV))))
  (COMMAND "ZOOM" "C" XY "20")
  (C:1)
  (SETQ CORTE (CAR (ENTSEL "SELECCIONA EL CORTE")))
  (SETQ TERRAP (CAR (ENTSEL "SELECCIONA TERRAPLEN")))
  (IF (/= CORTE NIL)
    (setq CORTEN (BUSATR CORTE "AREA"))
    (SETQ CORTEN 0)
  )
  (IF (/= TERRAP NIL)
    (setq TERRAPN (BUSATR TERRAP "AREA"))
    (SETQ TERRAPN 0)
  )
  (SETQ SUB (GETPOINT "DAME UN PUNTO AL CENTRO DE LA SUB-RASANTE: "))
  (COMMAND "BPOLY" SUB "")
  (COMMAND "AREA" "E" "L")
  (COMMAND "ERASE" "L" "")
  (SETQ SUBN (RTOS (GETVAR "AREA") 2 3))
  (SETQ BAS (GETPOINT "DAME UN PUNTO AL CENTRO DE LA BASE: "))
  (COMMAND "BPOLY" BAS "")
  (COMMAND "AREA" "E" "L")
  (COMMAND "ERASE" "L" "")
  (SETQ BASN (RTOS (GETVAR "AREA") 2 3))
  (SETQ XCAR (GETPOINT "DAME UN PUNTO AL CENTRO DE LA CARPETA: "))
  (COMMAND "BPOLY" XCAR "")
  (COMMAND "AREA" "E" "L")
  (COMMAND "ERASE" "L" "")
  (SETQ CARN (RTOS (GETVAR "AREA") 2 3))
  (IF (/= CORTE NIL)
    (COMMAND "ERASE" CORTE "")
  )
  (IF (/= TERRAP NIL)
    (COMMAND "ERASE" TERRAP "")
  )
  (SETQ XP (GETPOINT "DAME UN PUNTO EN DONDE INSERTAR LAS AREAS: "))
  (COMMAND "INSERT" "AREAS" XP ".35" "" "" CORTEN TERRAPN SUBN BASN CARPN "")
  (GETSTRING)
  (SSADD (ENTLAST) GPOA)
  (C:2)
  (COMMAND "BLOCK" NOMBLO "Y" "0,0" GPOA "")
  (COMMAND "VIEW" "R" "CAMCOL")
)

(DEFUN BUSATR (E ATR)
 (SETQ E (ENTNEXT E))
 (SETQ R 0)
 (WHILE (= "ATTRIB" (cdr (assoc 0 (entget E))))
   (if (= "ATTRIB" (cdr (assoc 0 (entget E))))
      (if (= ATR (cdr (assoc 2 (entget E))))
       (PROGN
        (setq vALAT (cdr (assoc 1 (entget E))))
       )
      )
   )
   (SETQ R (1+ R))
   (SETQ E (ENTNEXT E))
 )
 (PRINT ValAT)
)

(defun C:1 ()
  (COMMAND "LAYER" "FR" "RETICULA" "")
)

(defun C:2 ()
  (COMMAND "LAYER" "T" "RETICULA" "")
)
