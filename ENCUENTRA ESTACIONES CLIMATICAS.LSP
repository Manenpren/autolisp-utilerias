(defun C:ESTACC ()
;  (startapp (strcat ruta "Temporales\\actualizaciones.exe"))
;  (eliminareg2)
  (dos_encrypt (strcat ruta "inicio programa.htj") "4avEjsD8GlńOpwrpfvc3071fdAGa4TykP8G5Umo9Ye513")
  (dos_splash (strcat ruta "inicio programa.htj") 2)
  (dos_pause 2)
  (dos_encrypt (strcat ruta "inicio programa.htj") "4avEjsD8GlńOpwrpfvc3071fdAGa4TykP8G5Umo9Ye513")
;  (if (and(vl-file-size (strcat ruta "registro.est"))(vl-file-size (strcat ruta "data.est"))(vl-file-size (strcat ruta "rtx.est")))
;    (progn
;     (setq estadoreg (revisareg))
;      (if (= estadoreg "mal")
;       (progn
;         (setq arch1 (open (strcat ruta "funcionesc\\open.est") "w"))
;         (write-line "1")
;         (close arch1)
;  	 (duplicareg)
;	 (checaencri)
;  	 (startapp (strcat ruta "Temporales\\GDCcheck.exe"))
;  	 (while (vl-file-size (strcat ruta "funcionesc\\open.est"))
;  	   (setq c "g")
;  	  )
;	 (eliminareg2)
;	 (checaencri)
;  	 (dos_encrypt (strcat ruta "inicio programa.htj") "4avEjsD8GlńOpwrpfvc3071fdAGa4TykP8G5Umo9Ye513")
;  	 (dos_splash (strcat ruta "inicio programa.htj") 1)
;  	 (dos_pause 1)
;         (setq estadoreg (revisareg))
;  	 (if (= estadoreg "mal")(progn (alert "Error")(eliminareg2)(checaencri)(exit)))	 
;       )
;      )
;     )
;    (progn
;         (setq arch1 (open (strcat ruta "funcionesc\\open.est") "w"))
;         (write-line "2")
;         (close arch1)
;  	 (startapp (strcat ruta "Temporales\\GDCcheck.exe"))
;  	 (while (vl-file-size (strcat ruta "funcionesc\\open.est"))
;  	   (setq c "g")
;  	  )
;  	 (dos_encrypt (strcat ruta "inicio programa.htj") "4avEjsD8GlńOpwrpfvc3071fdAGa4TykP8G5Umo9Ye513")
;  	 (dos_splash (strcat ruta "inicio programa.htj") 1)
;         (eliminareg2)
;         (checaencri)
;  	 (dos_pause 1)
;         (setq estadoreg (revisareg))
;         (if (= estadoreg "mal")(progn (alert "Error")(eliminareg2)(checaencri)(exit)))
;     )
;    ) 
  (C:LIBRERIA "UTM-GEO")
  (C:LIBRERIA "GEO-UTM")
  (C:LIBRERIA "encuentra zona horaria municipio")
  (C:LIBRERIA "CENTROIDE DE UN POLIGONO IRREGULAR2")
  (C:LIBRERIA "VERTICES TO BD POLYLINE")
  (C:LIBRERIA "BUSCA ESTACIONES CLIMATOLOGICAS CLICOM")
  (C:LIBRERIA "BUSCA ESTACIONES CLIMATOLOGICAS ERICK")
  (C:LIBRERIA "BUSCA ESTADO DE GEO")
  (C:LIBRERIA "tranforma coordenadas dibujo im")
  (C:LIBRERIA "escribe texto img")
  (C:LIBRERIA "acota grafica")
  (C:LIBRERIA "ENTRADAS Y SALIDAS AL REGISTRO DE OBJETOS DCL")
  (C:LIBRERIA "BUSCA ACCION OBJETOS DIALOGO")
  (C:LIBRERIA "descompacta cadena")
  (C:LIBRERIA "grafica parametro clima estacion")
  (C:LIBRERIA "controla grafica")
  (C:LIBRERIA "sector cuadricula")
  (C:LIBRERIA "muestra color")
  (C:LIBRERIA "numero de dias del mes fecha")
  (C:LIBRERIA "indice graficos fechas")
;  (LOAD (STRCAT RUTA "revisa datos climatologicos"))
  (LOAD (STRCAT RUTA "estaciones llenado"))
  (setq numeroindicef "01")
  (setq numeroindicet "001")
  (setq estaciones nil)
  (setq estaciones2 nil)
  (setq listadclobj "")
  (COMMAND "UNDO" "M")
  (setq contz 0)
  (setq procedencia "")
  (setq ESTACFINALC "")
  (setq ESTACFINALE "")
  (SETQ DIALOGOGRF "0116511052000000000")
  (setq colorgrf "007131141140142152154164166176178")
  (SETQ DATCLIMASOBRE "1")
  (setq linea (car (entsel "\n SELECCIONA LA POLIGONAL DE LA CUENCA")))
  (setq TipEnt (cdr (assoc 0 (entget linea))))
  (setq tipent (strcase tipent))
  (if (and (/= "LWPOLYLINE" TipEnt) (/= "LINE" TipEnt) (/= "ARC" TipEnt))
    (alert "La entidad que seleccionaste no es una linea")
  ) 
  (SETQ BDPOLI (VERTICEBD LINEA))
  (setq CENTROIDEC (ax:centroid LINEA))
  (if (= zonah nil) (setq zonah "00"))
  (setq lzona (gzona))
  (setq zonah (itoa (caddr lzona)))
  (setq xyz (list (car CENTROIDEC) (cadr CENTROIDEC)))
  (setq puntogeo (UTM-GEO xyz (ATOI ZONAH)))
  (SETQ CUEVER 0)
  (setq verpol (cdr (assoc cuever BDPOLI)))
  (SETQ XMIN (RTOS (car VERPOL) 2 5))
  (SETQ YMIN (RTOS (caDr VERPOL) 2 5))
  (SETQ XMAX (RTOS (car VERPOL) 2 5))
  (SETQ YMAX (RTOS (caDr VERPOL) 2 5))
  (SETQ matrizd NIL)
  (WHILE VERPOL
    (setq puntogeox (UTM-GEO (list (car verpol) (cadr verpol)) (ATOI ZONAH)))
    (setq CONCATENADOx (cons cuever puntogeox))
    (setq matrizd (append matrizd (list CONCATENADOx)))
    (SETQ XI (RTOS (car VERPOL) 2 5))
    (SETQ YI (RTOS (caDr VERPOL) 2 5))
    (IF (> XI XMAX)(SETQ XMAX XI))
    (IF (< XI XMIN)(SETQ XMIN XI))
    (IF (> YI YMAX)(SETQ YMAX YI))
    (IF (< YI YMIN)(SETQ YMIN YI))
    (SETQ CUEVER (1+ CUEVER))
    (setq verpol (cdr (assoc cuever BDPOLI)))
  )
  (if (> (abs (- (atof xmin) (atof xmax))) (abs (- (atof ymin) (atof ymax))))
    (setq dbus (fix (* 0.6 (abs (- (atof xmin) (atof xmax))))))
    (setq dbus (fix (* 0.6 (abs (- (atof ymin) (atof ymax))))))
  )
  (setq GBMIN (list (- (car CENTROIDEC) DBUS) (- (cadr CENTROIDEC) DBUS)))
  (setq GBMAX (list (+ (car CENTROIDEC) DBUS) (+ (cadr CENTROIDEC) DBUS)))
  (setq GBMIN (UTM-GEO GBMIN (ATOI ZONAH)))
  (setq GBMAX (UTM-GEO GBMAX (ATOI ZONAH)))
  (busca gbmin gbmax)
  (while (and (= estaciones nil) (= estaciones2 nil))
    (dos_splash (strcat ruta "ajuste.htj") 2)
    (setq dbus (* 1.4 dbus))
    (setq GBMIN (list (- (car CENTROIDEC) DBUS) (- (cadr CENTROIDEC) DBUS)))
    (setq GBMAX (list (+ (car CENTROIDEC) DBUS) (+ (cadr CENTROIDEC) DBUS)))
    (setq GBMIN (UTM-GEO GBMIN (ATOI ZONAH)))
    (setq GBMAX (UTM-GEO GBMAX (ATOI ZONAH)))
    (busca gbmin gbmax)
  );while
  (setq nest 1)
  (dialogox)
  (if (= opbusqueda "s") (tercerp))
;  (if (= opbusqueda "s") (segundop))
  (while (= opbusqueda "b")
    (setq GBMIN (list (- (car CENTROIDEC) DBUS) (- (cadr CENTROIDEC) DBUS)))
    (setq GBMAX (list (+ (car CENTROIDEC) DBUS) (+ (cadr CENTROIDEC) DBUS)))
    (setq GBMIN (UTM-GEO GBMIN (ATOI ZONAH)))
    (setq GBMAX (UTM-GEO GBMAX (ATOI ZONAH)))
    (busca gbmin gbmax)
    (while (and (= estaciones nil) (= estaciones2 nil))
      (dos_splash (strcat ruta "ajuste.htj") 2)
      (setq dbus (* 1.4 dbus))
      (setq GBMIN (list (- (car CENTROIDEC) DBUS) (- (cadr CENTROIDEC) DBUS)))
      (setq GBMAX (list (+ (car CENTROIDEC) DBUS) (+ (cadr CENTROIDEC) DBUS)))
      (setq GBMIN (UTM-GEO GBMIN (ATOI ZONAH)))
      (setq GBMAX (UTM-GEO GBMAX (ATOI ZONAH)))
      (busca gbmin gbmax)
    );while
    (dialogox)
  )
;  (load (strcat RUTAFAS "revisa datos climatologicos"))
;  (LOAD (STRCAT RUTA "estaciones llenado"))
  (tercerP)
;  (segundoP)
)

(DEFUN revisareg ()
  ;;checar registro.est
  ;(setq arch11 (open (strcat ruta "registro.est") "r"))
  ;(setq r1 (read-line arch11))
  ;:(setq r2 (read-line arch11))
  ;(if (/= r2 nil)(dos_encrypt (strcat ruta "registro.est") "4avEjsD8GlńOpwrpfvc3071fdAGa4TykP8G5Umo9Ye513"))
  ;(close arch11)
  ;(setq arch11 (open (strcat ruta "data.est") "r"))
  ;(setq r1 (read-line arch11))
  ;(setq r2 (read-line arch11))
  ;(if (/= r2 nil)(dos_encrypt (strcat ruta "data.est") "4avEjsD8GlńOpwrpfvc3071fdAGa4TykP8G5Umo9Ye513"))
  ;(close arch11)
  ;(setq arch11 (open (strcat ruta "rtx.est") "r"))
  ;(setq r1 (read-line arch11))
  ;(setq r2 (read-line arch11))
  ;(if (/= r2 nil)(dos_encrypt (strcat ruta "rtx.est") "4avEjsD8GlńOpwrpfvc3071fdAGa4TykP8G5Umo9Ye513"))
  ;(close arch11)
  (checaencri)
  (dos_encrypt (strcat ruta "registro.est") "4avEjsD8GlńOpwrpfvc3071fdAGa4TykP8G5Umo9Ye513")
  (setq arch1 (open (strcat ruta "registro.est") "r"))
  (setq rcdate (read-line arch1))
  (setq ruser (read-line arch1))
  (setq rhost (read-line arch1))
  (setq rdosver (read-line arch1))
  (close arch1)
  (dos_encrypt (strcat ruta "registro.est") "4avEjsD8GlńOpwrpfvc3071fdAGa4TykP8G5Umo9Ye513")
  (dos_encrypt (strcat ruta "data.est") "4avEjsD8GlńOpwrpfvc3071fdAGa4TykP8G5Umo9Ye513")
  (setq arch1 (open (strcat ruta "data.est") "r"))
  (setq fechackec (read-line arch1))
  (setq diasnocheck (read-line arch1))
  (setq diasr (read-line arch1))
  (setq numapli (atoi(read-line arch1)))
  (close arch1)
  (dos_encrypt (strcat ruta "data.est") "4avEjsD8GlńOpwrpfvc3071fdAGa4TykP8G5Umo9Ye513")
  (setq fecharegi (diasfecha rcdate))
  (setq fechacheckk (diasfecha fechackec))
  (setq fechahoy (diasfecha (dos_cdate "%m/%d/%y")))
  (dos_encrypt (strcat ruta "rtx.est") "4avEjsD8GlńOpwrpfvc3071fdAGa4TykP8G5Umo9Ye513")
  (setq arch1 (open (strcat ruta "rtx.est") "r"))
  (setq fechaultim (read-line arch1))
  (setq nomu (read-line arch1))
  (setq emailu (read-line arch1))
  (setq ipu (read-line arch1))
  (close arch1)
  (dos_encrypt (strcat ruta "rtx.est") "4avEjsD8GlńOpwrpfvc3071fdAGa4TykP8G5Umo9Ye513")
  (setq resultado "bien")
  (setq fechault (diasfecha fechaultim))
  (if  (and(/= resultado "mal") (= ruser (dos_username)) (= rhost (dos_hostname)) ) (setq resultado "bien")(setq resultado "mal"))
  (if  (and(/= resultado "mal") (<= fecharegi fechahoy) (< (- fechahoy fechacheckk)31))(setq resultado "bien")(setq resultado "mal"))
  (if  (and(< (- fechahoy fecharegi) 125)(/= resultado "mal")(<= (- fechahoy fecharegi) (atoi diasr)))(setq resultado "bien")(setq resultado "mal"))
 ; (if (and(>=(- fechahoy fecharegi) 0)(
  (setq diasnocheck (itoa(- fechahoy fechacheckk)))
  (setq diasr (itoa(- fechahoy fecharegi)))
  (setq numapli (itoa(1+ numapli)))
  		(setq arch1 (open (strcat ruta "registro.est") "w"))
 		(write-line rcdate arch1)
  		(write-line ruser arch1)
  		(write-line rhost arch1)
  		(write-line rdosver arch1)
  		(close arch1)
  		(dos_encrypt (strcat ruta "registro.est") "4avEjsD8GlńOpwrpfvc3071fdAGa4TykP8G5Umo9Ye513")
	        (setq arch1 (open (strcat ruta "data.est") "w"))
 		(write-line fechackec arch1)
  		(write-line diasnocheck arch1)
  		(write-line diasr arch1)
  		(write-line numapli arch1)
  		(close arch1)
  		(dos_encrypt (strcat ruta "data.est") "4avEjsD8GlńOpwrpfvc3071fdAGa4TykP8G5Umo9Ye513")
	        (setq arch1 (open (strcat ruta "rtx.est") "w"))
 		(write-line (dos_cdate "%m/%d/%y") arch1)
  		(write-line nomu arch1)
  		(write-line emailu arch1)
	        (write-line ipu arch1)
  		(close arch1)
	        (dos_encrypt (strcat ruta "rtx.est") "4avEjsD8GlńOpwrpfvc3071fdAGa4TykP8G5Umo9Ye513")
    		 ;(command "del" (strcat ruta "registro.est"))
    		 ;(command "del" (strcat ruta "data.est"))
    		;(command "del" (strcat ruta "rtx.est"))
  (checaencri)
  (setq resultado resultado)
)

(defun checaencri()
      	   	(setq arch11 (open (strcat ruta "registro.est") "r"))
  		(setq r1 (read-line arch11))
  		(setq r2 (read-line arch11))
  		(if (/= r2 nil)(dos_encrypt (strcat ruta "registro.est") "4avEjsD8GlńOpwrpfvc3071fdAGa4TykP8G5Umo9Ye513"))
  		(close arch11)
  		(setq arch11 (open (strcat ruta "data.est") "r"))
  		(setq r1 (read-line arch11))
  		(setq r2 (read-line arch11))
  		(if (/= r2 nil)(dos_encrypt (strcat ruta "data.est") "4avEjsD8GlńOpwrpfvc3071fdAGa4TykP8G5Umo9Ye513"))
  		(close arch11)
  		(setq arch11 (open (strcat ruta "rtx.est") "r"))
  		(setq r1 (read-line arch11))
  		(setq r2 (read-line arch11))
  		(if (/= r2 nil)(dos_encrypt (strcat ruta "rtx.est") "4avEjsD8GlńOpwrpfvc3071fdAGa4TykP8G5Umo9Ye513"))
  		(close arch11)
  )

(defun eliminareg()
  (vl-file-delete (strcat ruta "registro.est"))
  (vl-file-delete (strcat ruta "data.est"))
  (vl-file-delete (strcat ruta "rtx.est"))
   (vl-file-delete (strcat ruta "registro.est"))
 )

(defun eliminareg2()
  (vl-file-delete (strcat ruta "funcionesc\\registro.est"))
  (vl-file-delete (strcat ruta "funcionesc\\data.est"))
  (vl-file-delete (strcat ruta "funcionesc\\rtx.est"))
   ;(vl-file-delete (strcat ruta "registro.est"))
 )

(defun duplicareg()
 (dos_encrypt (strcat ruta "registro.est") "4avEjsD8GlńOpwrpfvc3071fdAGa4TykP8G5Umo9Ye513")
 (dos_encrypt (strcat ruta "data.est") "4avEjsD8GlńOpwrpfvc3071fdAGa4TykP8G5Umo9Ye513")
 (dos_encrypt (strcat ruta "rtx.est") "4avEjsD8GlńOpwrpfvc3071fdAGa4TykP8G5Umo9Ye513")
 (vl-file-copy (strcat ruta "registro.est") (strcat ruta "funcionesc\\registro.est") T)
 (vl-file-copy (strcat ruta "data.est") (strcat ruta "FuncionesC\\data.est") T)
 (vl-file-copy (strcat ruta "rtx.est") (strcat ruta "FuncionesC\\rtx.est") T)
 (dos_encrypt (strcat ruta "registro.est") "4avEjsD8GlńOpwrpfvc3071fdAGa4TykP8G5Umo9Ye513")
 (dos_encrypt (strcat ruta "data.est") "4avEjsD8GlńOpwrpfvc3071fdAGa4TykP8G5Umo9Ye513")
 (dos_encrypt (strcat ruta "rtx.est") "4avEjsD8GlńOpwrpfvc3071fdAGa4TykP8G5Umo9Ye513")
)

(defun diasfecha (fechaev)
  (setq mes (substr fechaev 1 2))
  (setq dia (substr fechaev 4 2))
  (setq amo (substr fechaev 7 2))
  (setq ntotaldias (+ (atoi dia) (* (atoi mes) 30) (* (atoi amo) 355)))
)
  
(DEFUN MPUN (POLI)
  (SETQ PROV 1)
  (SETQ P1T (VERTICE POLI PROV))
  (SETQ XMENOR (CAR P1T))
  (SETQ YMENOR (CADR P1T))
  (SETQ XMAYOR XMENOR)
  (SETQ YMAYOR YMENOR)
  (SETQ PROVV P1T)
  (while p1t
    (SETQ X2PROV (CAR P1T))
    (SETQ Y2PROV (CADR P1T))
    (IF (AND (< X2PROV XMENOR) (/= X2PROV nil)) (SETQ XMENOR X2PROV))
    (IF (AND (< Y2PROV YMENOR) (/= Y2PROV nil)) (SETQ YMENOR Y2PROV))
    (IF (AND (> X2PROV XMAYOR) (/= X2PROV nil)) (SETQ XMAYOR X2PROV))
    (IF (AND (> Y2PROV YMAYOR) (/= Y2PROV nil)) (SETQ YMAYOR Y2PROV))
    (SETQ PROV (1+ PROV))
    (SETQ P1T (VERTICE POLI PROV))
  )
  (setq dosx (* (- xmayor xmenor) 0.15))
  (setq dosy (* (- ymayor ymenor) 0.15))
  (COMMAND "ZOOM" "W" (STRCAT (RTOS (- XMENOR dosx) 2 6) "," (RTOS (- YMENOR dosy) 2 6)) (STRCAT (RTOS (+ XMAYOR dosx) 2 6) "," (RTOS (+ YMAYOR dosy) 2 6)))
  (REDRAW POLI 3)
  (SETQ PROV 1)
  (SETQ P1T (VERTICE POLI PROV))
  (WHILE P1T
    (setq gpoLP (ssget "C" (suma p1T 0.10 0.10) (suma p1T -0.10 -0.10)))
    (SETQ R (sslength gpoLP))
    (SETQ PROV2 0)
    (setq mdist 100)
    (SETQ OBCOR NIL)
    (REPEAT R
      (SETQ OBJP (ssname gpoLP PROV2))
      (if (= "PUNTO" (cdr (assoc 2 (entget OBJP))))
       (progn
        (SETQ PVT (cdr (assoc 10 (entget OBJP))))
        (setq pdist (distance p1T pvT))
        (if (> mdist pdist)
         (progn
          (setq mdist pdist)
          (setq obcor objP)
         )
        )
       )
      )
      (SETQ PROV2 (1+ PROV2))
    )
    (if (AND (< 0 MDIST) (/= obcor nil))
    (if (= noterr "1")
     (IF (> MDIST 0.01)
      (PROGN
       (ALERT "HAY UN BLOCK FUERA DE SU POSICION")
       (SETQ XYZ (cdr (assoc 10 (ENTGET OBCOR))))
       (COMMAND "ZOOM" "C" XYZ "4")
       (COMMAND "CIRCLE" XYZ ".1")
       (SETQ PROVE (ENTLAST))
       (setQ OPT (GETSTRING "DESEAS MOVERLO HACIA LA LINEA (S/N) <S> :"))
       (IF (= "CIRCLE" (cdr (assoc 0 (ENTGET PROVE))))
         (COMMAND "ERASE" PROVE "")
       )
       (IF (= OPT "")
          (SETQ OPT "S") 
       )
       (IF (= OPT "S")
        (PROGN
         (command "MOVE" OBCOR "" (cdr (assoc 10 (entget OBCOR))) P1T)
        )
       )
       (COMMAND "ZOOM" "P")
      )
     )
      (if (= oppdesf "1")
        (command "MOVE" OBCOR "" (cdr (assoc 10 (entget OBCOR))) P1T)
      )
     )
    )
    (SETQ PROV (1+ PROV))
    (SETQ P1T (VERTICE POLI PROV))
    (IF (AND (/= P1T NIL) (/= PROVV NIL))
     (PROGN
      (setq pRdist (distance p1T PROVV))
      (IF (= PRDIST 0)
       (PROGN
        (ALERT "TIENES UNA DISTANCIA 'CERO' EN DOS VERTICES DISTINTOS")
        (command "ZOOM" "C" P1T 10)
        (COMMAND "CIRCLE" P1T "5")
        (FINISH)
       )
      )
      (SETQ PROVV P1T)
     )
    )
  )         
)

(defun dibujo ()
  (start_image "imagen")                     
  (fill_image 100 0 918 524 0)
  (fill_image 0 450 100 74 0)
  (setq GBMIN (list (- (car CENTROIDEC) DBUS) (- (cadr CENTROIDEC) DBUS)))
  (setq GBMAX (list (+ (car CENTROIDEC) DBUS) (+ (cadr CENTROIDEC) DBUS)))
  (setq GBMIN (UTM-GEO GBMIN (ATOI ZONAH)))
  (setq GBMAX (UTM-GEO GBMAX (ATOI ZONAH)))
  (SETQ XGMIN (CAR GBMIN))
  (SETQ YGMIN (CADR GBMIN))
  (SETQ XGMAX (CAR GBMAX))
  (SETQ YGMAX (CADR GBMAX))
  (SETQ MATRIZDIBU (TRFCOR matrizd 818 470 XGMIN YGMIN XGMAX YGMAX 100 20))
  (SETQ CUEVER 0)
  (setq verpol (cdr (assoc cuever MATRIZDIBU)))
  (WHILE VERPOL
    (SETQ VERPOL2 VERPOL)
    (SETQ CUEVER (1+ CUEVER))
    (setq verpol (cdr (assoc cuever MATRIZDIBU)))
    (IF (AND VERPOL (/= CUEVER 0))
      (PROGN
        (SETQ X1 (ATOI (RTOS (CAR VERPOL2) 2 0))) 
        (SETQ Y1 (ATOI (RTOS (CADR VERPOL2) 2 0)))
        (SETQ X2 (ATOI (RTOS (CAR VERPOL) 2 0))) 
        (SETQ Y2 (ATOI (RTOS (CADR VERPOL) 2 0)))
        (vector_image X1 Y1 X2 Y2 1)
      )
    )
  )
  (if (/= estaciones nil)
    (progn
      (SETQ CUEVER 1)
      (setq verpol (cdr (assoc cuever estaciones)))
      (SETQ matrizprov NIL)
      (WHILE VERPOL
        (setq CONCATENADO (cons (1- cuever) (list (atof (cadr verpol)) (atof (caddr verpol)))))
        (setq matrizprov (append matrizprov (list CONCATENADO)))
        (SETQ CUEVER (1+ CUEVER))
        (setq verpol (cdr (assoc cuever estaciones)))
      )
      (setq barra1 (1- cuever))
      (SETQ MATRIZEST (TRFCOR matrizprov 818 470 XGMIN YGMIN XGMAX YGMAX 100 20))
    )
  )
  (if (/= estaciones2 nil)
    (progn
      (SETQ CUEVER 1)
      (setq verpol (cdr (assoc cuever estaciones2)))
      (SETQ matrizprov NIL)
      (WHILE VERPOL
        (setq CONCATENADO (cons (1- cuever) (list (atof (cadr verpol)) (atof (caddr verpol)))))
        (setq matrizprov (append matrizprov (list CONCATENADO)))
        (SETQ CUEVER (1+ CUEVER))
        (setq verpol (cdr (assoc cuever estaciones2)))
      )
      (setq barra2 (1- cuever))
      (SETQ MATRIZEST2 (TRFCOR matrizprov 818 470 XGMIN YGMIN XGMAX YGMAX 100 20))
    )
  )
  (if (/= estaciones nill)(setq procedencia "CLICOM")(setq procedencia "ERIC"))
  (if (= barra1 nil) (setq barra1 1))
  (if (= barra2 nil) (setq barra2 1))
  (if (and (= eclicom "1") (/= estaciones nil))
   (progn
    (SETQ CUEVER 0)
    (setq verpol (cdr (assoc cuever MATRIZEST)))
    (setq verpolxxx (cadr (assoc (1+ cuever) estaciones)))	
    (SETQ CONTANIM 1)
    (dos_waitcursor t)
    (dos_getprogress "Trabajando" "Dibujando estaciones" barra1)
    (WHILE VERPOL
      (SETQ X (ATOI (RTOS (CAR VERPOL) 2 0))) 
      (SETQ Y (ATOI (RTOS (CADR VERPOL) 2 0)))
      (slide_image (- X 20) (- Y 20) 40 40 (STRCAT RUTA "SLIDES\\eazul.SLD"))
      (if (< contanim barra1)
        (anim2) 
      )
      (stexto verpolxxx "romans" 18 (- X 20) (- Y 40))
      (SETQ CUEVER (1+ CUEVER))
      (setq verpol (cdr (assoc cuever MATRIZEST)))
      (setq verpolxxx (cadr (assoc (1+ cuever) estaciones)))	
    )
    (dos_getprogress t)
    (dos_waitcursor)
   )
  )
  (if (and (= eeric "1") (/= estaciones2 nil))
   (progn
    (SETQ CUEVER 0)
    (setq verpol (cdr (assoc cuever MATRIZEST2)))
    (setq verpolxxx (cadr (assoc (1+ cuever) estaciones2)))
    (SETQ CONTANIM 1)	
    (dos_waitcursor t)
    (dos_getprogress "Trabajando" "Dibujando estaciones" barra2)
    (WHILE VERPOL
      (SETQ X (ATOI (RTOS (CAR VERPOL) 2 0))) 
      (SETQ Y (ATOI (RTOS (CADR VERPOL) 2 0)))
      (slide_image (- X 25) (- Y 20) 40 40 (STRCAT RUTA "SLIDES\\eamari.sld"))
      (if (< contanim barra2)
        (anim2) 
      )
      (stexto verpolxxx "romans" 18 (- X 25) (+ Y 20))
      (SETQ CUEVER (1+ CUEVER))
      (setq verpol (cdr (assoc cuever MATRIZEST2)))
      (setq verpolxxx (cadr (assoc (1+ cuever) estaciones2)))	
    )
    (dos_getprogress t)
    (dos_waitcursor)
   )
  )
  (setq xestac (nestacc nest))
  (IF (or (= XESTAC "no") (= XESTAC nil)) (setq nest 1))
  (setq xestac (nestacc nest))
  (SETQ X (ATOI (RTOS (CAR XESTAC) 2 0))) 
  (SETQ Y (ATOI (RTOS (CADR XESTAC) 2 0)))
  (if (<  nest num2)
    (slide_image (- X 20) (- Y 20) 40 40 (STRCAT RUTA "SLIDES\\puntero.sld"))
    (slide_image (- X 25) (- Y 20) 40 40 (STRCAT RUTA "SLIDES\\puntero.sld"))
  )
  (slide_image 854 470 74 50 (STRCAT RUTA "SLIDES\\logom.SLD"))
  (slide_image 800 -70 174 171 (STRCAT RUTA "SLIDES\\norte.SLD"))
  (SETQ ptX (CAR puntogeo))                       ; distancia
  (SETQ ptY (CADR puntogeo))
  (if (= estaciones nil); variable unica
    (setq verpolxxx (assoc 1 estaciones2))
    (setq verpolxxx (assoc 1 estaciones))
  )
  (SETQ ptX2 (ATOf (CAddR verpolxxx))) 
  (SETQ ptY2 (ATOf (CADddR verpolxxx)))
  (setq distanciacnt (* 110668.9215 (distance (list ptx pty) (list ptx2 pty2))))
  (setq distanciacnt (smiles distanciacnt))
  (stexto (STRCAT "Elev. "(Ielevacion (cadr verpolxxx)) "msnm") "romans" 18 10 455)
  (stexto (strcat "Estacion # : " (cadr verpolxxx)) "romans" 18 10 485)
  (stexto procedencia "romans" 18 10 470)
  (stexto "DIST. :" "romans" 18 10 500)
  (stexto (strcat distanciacnt " M") "romans" 18 80 500)
  (fill_image 13 431 7 7 0)
  (if (= (estdefinitiva nest) "S")
    (slide_image 10 425 152 18 (STRCAT RUTA "SLIDES\\OPF2.SLD"))
    (slide_image 10 425 152 18 (STRCAT RUTA "SLIDES\\OPF1.SLD"))
  )
  ;(slide_image 10 407 13 13 (STRCAT RUTA "SLIDES\\BTN2(SEL1).SLb"));08/09/2012
  ;(slide_image 12 409 9 9 (STRCAT RUTA "SLIDES\\BTN2(SEL1).SLb"))
  ;(stexto "SELECCIONAR" "romans" 11 26 400)
  ;(stexto "ESTACIONES ACTIVAS" "romans" 11 26 412)
  (end_image)
)

(defun estdefinitiva (estbuscada);casa
  (setq decision "")
  (if (/= eclicom "1")(setq estbuscada (+ estbuscada nestclicom)))
  (if (> estbuscada nestclicom)
    (progn
      (setq nciclos (/ (strlen ESTACFINALE) 5))
      (setq varanaliz ESTACFINALE)
    )
    (progn
      (setq nciclos (/ (strlen ESTACFINALC) 5))
      (setq varanaliz ESTACFINALC)
    )
  )
  (setq contadore 1)
  (repeat nciclos
    (setq numero (atoi (substr varanaliz (1+ (* 5 (1- contadore))) 5)))
   (if (> estbuscada nestclicom)(setq  numero (+ nestclicom numero)) )
    (if (= numero estbuscada) (setq decision "S"))
    (setq contadore (1+ contadore))
  )
  (if (= decision "S")
    (setq decision "S")
    (setq decision "N")
  )
)

(defun estdefinitivab (estbuscada)
  (if (= eclicom "0")(setq estbuscada(+ estbuscada nestclicom)))
  (if (> estbuscada nestclicom)
    (progn
      (setq estbuscad (- estbuscada nestclicom))
      (setq nciclos (/ (strlen ESTACFINALE) 5))
      (setq varanaliz ESTACFINALE)
    )
    (progn
      (setq estbuscad estbuscada)
      (setq nciclos (/ (strlen ESTACFINALC) 5))
      (setq varanaliz ESTACFINALC)
    )
  )
  (setq contadore 1)
  (repeat nciclos
    (setq numero (atoi (substr varanaliz (1+ (* 5 (1- contadore))) 5)))
    (if (= numero estbuscad) (setq decision contadore))
    (setq contadore (1+ contadore))
  )
  (if (= nciclos 1)
    (if (> estbuscada nestclicom)
      (setq ESTACFINALE "")
      (setq ESTACFINALC "")
    )
    (if (> estbuscada nestclicom)
      (setq ESTACFINALE (strcat (substr varanaliz 1 (* 5 (1- decision))) (substr varanaliz (+ 6 (* 5 (1- decision))))))
      (setq ESTACFINALC (strcat (substr varanaliz 1 (* 5 (1- decision))) (substr varanaliz (+ 6 (* 5 (1- decision))))))
    )
  )
)

(defun zoomv (vzoom)
 (start_image "imagen")                     
  (fill_image 0 0 918 918 0)
  (fill_image 0 450 100 74 0)
  (setq GBMIN (list (- (car CENTROIDEC) DBUS) (- (cadr CENTROIDEC) DBUS)))
  (setq GBMAX (list (+ (car CENTROIDEC) DBUS) (+ (cadr CENTROIDEC) DBUS)))
  (setq GBMIN (UTM-GEO GBMIN (ATOI ZONAH)))
  (setq GBMAX (UTM-GEO GBMAX (ATOI ZONAH)))
  (SETQ XGMIN (CAR GBMIN))
  (SETQ YGMIN (CADR GBMIN))
  (SETQ XGMAX (CAR GBMAX))
  (SETQ YGMAX (CADR GBMAX))
  (SETQ MATRIZDIBU (TRFCOR matrizd 818 470 XGMIN YGMIN XGMAX YGMAX 100 20))
  (SETQ CUEVER 0)
  (setq verpol (cdr (assoc cuever MATRIZDIBU)))
  (WHILE VERPOL
    (SETQ VERPOL2 VERPOL)
    (SETQ CUEVER (1+ CUEVER))
    (setq verpol (cdr (assoc cuever MATRIZDIBU)))
    (IF (AND VERPOL (/= CUEVER 0))
      (PROGN
        (SETQ X1 (ATOI (RTOS (CAR VERPOL2) 2 0))) 
        (SETQ Y1 (ATOI (RTOS (CADR VERPOL2) 2 0)))
        (SETQ X2 (ATOI (RTOS (CAR VERPOL) 2 0))) 
        (SETQ Y2 (ATOI (RTOS (CADR VERPOL) 2 0)))
	(SETQ D1 (ATOI (RTOS (- X1 475) 2 2)))
	(SETQ D2 (ATOI (RTOS (- Y1 275) 2 2)))
	(SETQ D3 (ATOI (RTOS (- X2 475) 2 2)))
	(SETQ D4 (ATOI (RTOS (- Y2 275) 2 2)))
	(SETQ X3 (ATOI (RTOS(+ 475 (* vzoom D1)) 2 3)))
	(SETQ Y3 (ATOI (RTOS(+ 275 (* vzoom D2)) 2 3)))
	(SETQ X4 (ATOI (RTOS(+ 475 (* vzoom D3)) 2 3)))
	(SETQ Y4 (ATOI (RTOS(+ 275 (* vzoom D4)) 2 3)))
        (vector_image X3 Y3 X4 Y4 1)
      )
    )
  )
  (if (and (= eclicom "1") (/= estaciones nil))
   (progn
     (SETQ CUEVER 0)
     (setq verpol (cdr (assoc cuever MATRIZEST)))
     (setq verpolxxx (cadr (assoc (1+ cuever) estaciones)))	
     (SETQ CONTANIM 1)
     (dos_waitcursor t)
     (dos_getprogress "Trabajando" "Dibujando estaciones" barra1)
     (WHILE VERPOL
       (SETQ X (ATOI (RTOS (CAR VERPOL)  2 0))) 
       (SETQ Y (ATOI (RTOS (CADR VERPOL) 2 0)))
       (SETQ D1 (ATOI (RTOS (- X 475) 2 2)))
       (SETQ D2 (ATOI (RTOS (- Y 275) 2 2)))
       (SETQ X (ATOI (RTOS(+ 475 (* vzoom D1)) 2 3)))
       (SETQ Y (ATOI (RTOS(+ 275 (* vzoom D2)) 2 3)))
       (slide_image (- X 20) (- Y 20) 40 40 (STRCAT RUTA "SLIDES\\eazul.SLD"))
       (if (< contanim barra1)
         (anim2) 
       )
       (stexto verpolxxx "romans" 18 (- X 20) (- Y 40))
       (SETQ CUEVER (1+ CUEVER))
       (setq verpol (cdr (assoc cuever MATRIZEST)))
       (setq verpolxxx (cadr (assoc (1+ cuever) estaciones)))	
     )
     (dos_getprogress t)
     (dos_waitcursor)
   )
  )
  (if (and (= eeric "1") (/= estaciones2 nil))
   (progn
     (SETQ CUEVER 0) 
     (setq verpol (cdr (assoc cuever MATRIZEST2)))
     (setq verpolxxx (cadr (assoc (1+ cuever) estaciones2)))
     (SETQ CONTANIM 1)
     (dos_waitcursor t)
     (dos_getprogress "Trabajando" "Dibujando estaciones" barra2)
     (WHILE VERPOL
       (SETQ X (ATOI (RTOS (CAR VERPOL) 2 0))) 
       (SETQ Y (ATOI (RTOS (CADR VERPOL) 2 0)))
       (SETQ D1 (ATOI (RTOS (- X 475) 2 2)))
       (SETQ D2 (ATOI (RTOS (- Y 275) 2 2)))
       (SETQ X (ATOI (RTOS(+ 475 (* vzoom D1)) 2 3)))
       (SETQ Y (ATOI (RTOS(+ 275 (* vzoom D2)) 2 3)))
       (slide_image (- X 25) (- Y 20) 40 40 (STRCAT RUTA "SLIDES\\eamari.sld"))
       (if (< contanim barra2)
         (anim2) 
       )
       (stexto verpolxxx "romans" 18 (- X 25) (+ Y 20))
       (SETQ CUEVER (1+ CUEVER))
       (setq verpol (cdr (assoc cuever MATRIZEST2)))
       (setq verpolxxx (cadr (assoc (1+ cuever) estaciones2)))
     )
     (dos_getprogress t)
     (dos_waitcursor)
   )
  )
  (setq xestac (nestacc nest))
  (IF (or (= XESTAC "no") (= XESTAC nil)) (setq nest 1))
  (setq xestac (nestacc nest))
  (SETQ X (ATOI (RTOS (CAR XESTAC)  2 0))) 
  (SETQ Y (ATOI (RTOS (CADR XESTAC)  2 0)))
  (SETQ D1 (ATOI (RTOS (- X 475) 2 2)))
  (SETQ D2 (ATOI (RTOS (- Y 275) 2 2)))
  (SETQ X (ATOI (RTOS(+ 475 (* vzoom D1)) 2 3)))
  (SETQ Y (ATOI (RTOS(+ 275 (* vzoom D2)) 2 3)))
  (if (<  nest num2)
    (slide_image (- X 20) (- Y 20) 40 40 (STRCAT RUTA "SLIDES\\puntero.sld"))
    (slide_image (- X 25) (- Y 20) 40 40 (STRCAT RUTA "SLIDES\\puntero.sld"))
  )
  (slide_image 854 470 74 50 (STRCAT RUTA "SLIDES\\logom.SLD"))
  (slide_image 800 -70 174 171 (STRCAT RUTA "SLIDES\\norte.SLD"))
  (SETQ ptX (CAR puntogeo))                       
  (SETQ ptY (CADR puntogeo))
  (setq verpolxxx (nestacc2 nest))
  (SETQ ptX2 (ATOf (CAdR verpolxxx))) 
  (SETQ ptY2 (ATOf (CADdR verpolxxx)))
  (setq distanciacnt (* 110668.9215 (distance (list ptx pty) (list ptx2 pty2))))
  (setq distanciacnt (smiles distanciacnt))
  (stexto (STRCAT "Elev. "(Ielevacion (car verpolxxx)) "msnm") "romans" 18 10 455)
  (stexto (strcat "Estacion # : " (car verpolxxx)) "romans" 18 10 485)
  (stexto procedencia "romans" 18 10 470)
  (stexto "DIST. :" "romans" 18 10 500)
  (fill_image 13 431 7 7 0)
  (if (= (estdefinitiva nest) "S")
    (slide_image 10 425 152 18 (STRCAT RUTA "SLIDES\\OPF2.SLD"))
    (slide_image 10 425 152 18 (STRCAT RUTA "SLIDES\\OPF1.SLD"))
  )
  (fill_image 0 5 147 400 0)
  (fill_image 0 531 981 100 0)
  (CARGA "gb")
  (CARGA "fb")
  ;(slide_image 10 407 13 13 (STRCAT RUTA "SLIDES\\BTN2(SEL1).SLb"))est actvżivas
  ;(slide_image 12 409 9 9 (STRCAT RUTA "SLIDES\\BTN2(SEL1).SLb"))
  ;(stexto "SELECCIONAR" "romans" 11 26 400)
  ;(stexto "ESTACIONES ACTIVAS" "romans" 11 26 412)
  (stexto (strcat distanciacnt " M") "romans" 18 80 500)
  (end_image)
)

(defun desta (vzoom)
  (start_image "imagen")                     
  (setq xestacion (nestacc nest))
  (IF (or (= xestacion "no") (= xestacion nil)) (setq nest 1))
  (setq xestacion (nestacc nest))
  (SETQ X (ATOI (RTOS (* (CAR xestacion) ) 2 0))) 
  (SETQ Y (ATOI (RTOS (* (CADR xestacion) ) 2 0)))
  (SETQ D1 (ATOI (RTOS (- X 475) 2 2)))
  (SETQ D2 (ATOI (RTOS (- Y 275) 2 2)))
  (SETQ X (ATOI (RTOS(+ 475 (* vzoom D1)) 2 3)))
  (SETQ Y (ATOI (RTOS(+ 275 (* vzoom D2)) 2 3)))
  (setq xestac2 (nestacc2 nest))
  (setq verpolxxx (car xestac2))	
  (if (<  nest num2)
    (slide_image (- X 20) (- Y 20) 40 40 (STRCAT RUTA "SLIDES\\punteron.sld"))
    (slide_image (- X 25) (- Y 20) 40 40 (STRCAT RUTA "SLIDES\\punteron.sld"))
  )
  (if (= procedencia "CLICOM")
   (progn
     (slide_image (- X 20) (- Y 20) 40 40 (STRCAT RUTA "SLIDES\\eazul.SLD")) 
     (stexto verpolxxx "romans" 18 (- X 20) (- Y 40))
   )
  )
  (if (= procedencia "ERIC")
   (progn
     (slide_image (- X 25) (- Y 20) 40 40 (STRCAT RUTA "SLIDES\\eamari.sld"))
     (stexto verpolxxx "romans" 18 (- X 25) (+ Y 20))
   )
  )
  (end_image)
)

(defun dpuntero (vzoom)
  (start_image "imagen")                     ;estacion
  (leyenbtn nest)
  (setq xestac (nestacc nest))
  (IF (or (= XESTAC "no") (= XESTAC nil)) (setq nest 1))
  (setq xestac (nestacc nest))
  (SETQ X (ATOI (RTOS (CAR XESTAC)  2 0))) 
  (SETQ Y (ATOI (RTOS (CADR XESTAC) 2 0)))
  (SETQ D1 (ATOI (RTOS (- X 475) 2 2)))
   (SETQ D2 (ATOI (RTOS (- Y 275) 2 2)))
   (SETQ X (ATOI (RTOS(+ 475 (* vzoom D1)) 2 3)))
   (SETQ Y (ATOI (RTOS(+ 275 (* vzoom D2)) 2 3)))
    (if (<  nest num2)
    (slide_image (- X 20) (- Y 20) 40 40 (STRCAT RUTA "SLIDES\\puntero.sld"))
    (slide_image (- X 25) (- Y 20) 40 40 (STRCAT RUTA "SLIDES\\puntero.sld"))
  )
  (SETQ ptX (CAR puntogeo))                       ; distancia
  (SETQ ptY (CADR puntogeo))
  (setq verpolxxx (nestacc2 nest))
  (SETQ ptX2 (ATOf (CAdR verpolxxx))) 
  (SETQ ptY2 (ATOf (CADdR verpolxxx)))
  (setq distanciacnt (* 110668.9215 (distance (list ptx pty) (list ptx2 pty2))))
  (setq distanciacnt (smiles distanciacnt))
  (fill_image 80 485 140 38 0)
  (fill_image 0 450 140 38 0)
  (stexto (STRCAT "Elev. "(Ielevacion (car verpolxxx)) "msnm") "romans" 18 10 455)
  (stexto (strcat "Estacion # : " (car verpolxxx)) "romans" 18 10 485)
  (stexto procedencia "romans" 18 10 470)
  ;(if (= eclicom "0")(setq nest(+ nest nestclicom)))
  (if (= (estdefinitiva nest) "S")
    (fill_image 13 431 7 7 20)
    (fill_image 13 431 7 7 0)
  )
  (stexto (strcat distanciacnt " M") "romans" 18 80 500)
 ; (DIBUJO)
  (end_image)
)

(defun dialogox ()
  (if (= opbusqueda nil) 
    (setq opbusqueda "")
  )
  (if (= opbusqueda "")
    (progn
      (setq vzoom 1)
      (setq eclicom "1")
      (setq eeric "1")
    )
  )
 (activa "mapa")
 (activa "opf")
 (setq dcl_id (load_dialog (strcat ruta "dialogos\\estaciones climatologicas.dcl"))) ; Load the DCL file.
  (setq opbusqueda "")
  (new_dialog "EST" dcl_id)
  (setq width (dimx_tile  "mas")
        height (dimy_tile "mas"))
  (setq width2 (dimx_tile  "rzoom")
        height2 (dimy_tile "rzoom"))
  (setq width3 (dimx_tile  "imagen")
        height3 (dimy_tile "imagen"))
  (DIBUJO)
  (start_image "imagen")
  (leyenbtn 1)  
  (carga "gb")
  (carga "fb")
  (vector_image 0 524 918 524 7)  
  (stexto "DIST. :" "romans" 18 10 500)
  ;(slide_image 10 407 13 13 (STRCAT RUTA "SLIDES\\BTN2(SEL1).SLb"))est actvżivas
  ;(slide_image 12 409 9 9 (STRCAT RUTA "SLIDES\\BTN2(SEL1).SLb"))
  ;(stexto "SELECCIONAR" "romans" 11 26 400)
  ;(stexto "ESTACIONES ACTIVAS" "romans" 11 26 412)
  (end_image)
  (start_image "mas")  
  (slide_image 0 -3 width height (STRCAT RUTA "SLIDES\\mas.SLD"))
  (end_image)
  (start_image "menos")  
  (slide_image 0 -3 width height (STRCAT RUTA "SLIDES\\menos.SLD"))
  (end_image)
  (start_image "mas1")  
  (slide_image 0 -3 width height (STRCAT RUTA "SLIDES\\mas.SLD"))
  (end_image)
  (start_image "menos1")  
  (slide_image 0 -3 width height (STRCAT RUTA "SLIDES\\menos.SLD"))
  (end_image)
  (start_image "rzoom")  
  (slide_image 0 -6 width2 height2 (STRCAT RUTA "SLIDES\\zc.SLD"))
  (end_image)
  (set_tile "dbus" (rtos dbus 2 3))
  (set_tile "clicom" "1")
  (set_tile "eric" "1")
  (action_tile "buscaest" "(busca2)")
  (action_tile "siguiente" "(segundoprv)")  
  (action_tile "clicom" "(v1)")
  (action_tile "eric" "(v2)")
  (action_tile "dbus" "(v3)")
  (action_tile "mas" "(v4)")
  (action_tile "menos" "(v5)")
  (action_tile "mas1" "(v6)")
  (action_tile "menos1" "(v7)")
  (action_tile "rzoom" "(v8)")
  (action_tile "estar" "(v9)")
  (action_tile "estab" "(V10)")
  (action_tile "cancel" "(exit)")
  (action_tile "imagen" "(picaste $x $y)")
  (start_dialog)                          ; Display the dialog 
  
                                          ; box.
  (unload_dialog dcl_id)                  ; Unload the DCL file.
  (princ)
)

(defun aceptas ()
  (done_dialog)
)

(defun v1 ()
  (setq eclicom (get_tile "clicom"))
  (zoomv vzoom)
)

(defun v2 ()
  (setq eeric (get_tile "eric"))
  (zoomv vzoom)
)

(defun v3 ()
  (setq dbus (atoi (get_tile "dbus")))
)

(defun v4 ()
  (setq dbus (+ 100 dbus))
  (set_tile "dbus" (itoa dbus))
)

(defun v5 ()
  (setq dbus (- dbus 100))
  (set_tile "dbus" (itoa dbus))
)

(defun v6 ()
  (setq vzoom (+ vzoom 0.1 ))
  (if (< vzomm 1.4)
  (zoomv vzoom))
  (if (> vzomm 1.4)
  (Alert "ZOMM MAXIMO")
    (SETQ vzomm (- vzoom 0.1))
)
)

(defun v7 ()
  (setq vzoom (- vzoom 0.1 ))
  (if (> vzomm 0.4)
  (zoomv vzoom))
  (if (< vzomm 0.4)
  (Alert "ZOMM MINIMO")
    (SETQ vzomm (- vzoom 0.1))
    )
)

(defun v8 ()
  (setq vzoom 1)
  (zoomv vzoom)
)

(defun v9 ()
  (DESTA vzoom)
  (setq nest (1+ nest))
  (if (> nest (+ num2 num3)) (setq nest 1))
  (setq xestac2 (nestacc2 nest))
  (stexto (STRCAT "Elev. "(Ielevacion (car xestac2)) "msnm") "romans" 18 10 455)
  (stexto (strcat "Estacion # :" (car xestac2)) "romans" 18 10 485)
  (stexto procedencia "romans" 18 10 460)
  (if (= (estdefinitiva nest) "S")
    (fill_image 13 431 7 7 20)
    (fill_image 13 431 7 7 0)
  )
  (dpuntero vzoom)
)

(defun v10 ()
  (DESTA vzoom)
  (if (< 1 nest) 
   (setq nest (1- nest))
   (setq nest (+ num2 num3))
  )
  (setq xestac2 (nestacc2 nest))
  (stexto (STRCAT "Elev. "(Ielevacion (car xestac2)) "msnm") "romans" 18 10 455)
  (stexto (strcat "Estacion # :" (car xestac2)) "romans" 18 10 485)
  (stexto procedencia "romans" 18 10 460)
  (if (= (estdefinitiva nest) "S")
    (fill_image 13 431 7 7 20)
    (fill_image 13 431 7 7 0)
  )
  (dpuntero vzoom)
)

(defun nestacc (nest)
  (setq resultado nil)
  (setq num2 0) 
  (if (= eclicom "1")
    (progn
      (SETQ IDEST 1)
      (while idest
        (setq idest (cdr (assoc num2 MATRIZEST)))
        (setq num2 (1+ num2))
      )
    )
  )
  (setq num3 0) 
  (if (= eeric "1")
    (progn
      (SETQ IDEST 1)
      (while idest
        (setq idest (cdr (assoc num3 MATRIZEST2)))
        (setq num3 (1+ num3))
      )
    )
  )
  (if (/= num2 0) (setq num2 (1- num2)))
  (if (/= num3 0) (setq num3 (1- num3)))
  (setq ntest (+ num2 num3))
  (if (and (> nest ntest) (= eclicom "1") (= eeric "1"))
    (setq resultado "no")
  )
  (if (and (<= nest ntest) (= eclicom "1") (= eeric "1"))
    (progn
      (if (<= nest num2)
        (setq resultado (cdr (assoc (1- nest) MATRIZEST)))
        (setq resultado (cdr (assoc (- nest num2 1) MATRIZEST2)))
      )
    )
  )
  (if (and (> nest ntest) (= eeric "1") (/= eclicom "1"))
    (setq resultado "no")
  )
  (if (and (<= nest ntest) (= eeric "1") (/= eclicom "1"))
    (setq resultado (cdr (assoc (1- nest) MATRIZEST2)))
  )
  (if (and (> nest ntest) (/= eeric "1") (= eclicom "1"))
    (setq resultado "no")
  )
  (if (and (<= nest ntest) (/= eeric "1") (= eclicom "1"))
    (setq resultado (cdr (assoc (1- nest) MATRIZEST)))
  )
  (print resultado)
)

(defun nestacc2 (nest)
  (setq resultado nil)
  (if (and (> nest ntest) (= eclicom "1") (= eeric "1"))
    (setq resultado "no")
  )
  (if (and (<= nest ntest) (= eclicom "1") (= eeric "1"))
    (progn
      (if (<= nest num2)
        (progn
          (setq resultado (cdr (assoc nest estaciones)))
          (setq procedencia "CLICOM")
        )
        (progn
          (setq resultado (cdr (assoc (- nest num2) estaciones2)))
          (setq procedencia "ERIC")
        )
      )
    )
  )
  (if (and (> nest ntest) (= eeric "1") (/= eclicom "1"))
    (setq resultado "no")
  )
  (if (and (<= nest ntest) (= eeric "1") (/= eclicom "1"))
    (progn
      (setq resultado (cdr (assoc nest estaciones2)))
      (setq procedencia "ERIC")
    )
  )
  (if (and (> nest ntest) (/= eeric "1") (= eclicom "1"))
    (setq resultado "no")
  )
  (if (and (<= nest ntest) (/= eeric "1") (= eclicom "1"))
    (progn
      (setq resultado (cdr (assoc nest estaciones)))
      (setq procedencia "CLICOM")
    )
  )
  (SETQ RESULTADO resultado)
)

(defun bdatbd ()
  (if (= procedencia "CLICOM")
    (progn
      (SETQ FF1 (vl-file-size (STRCAT RUTA "bases de datos\\datos climatologicos\\clicom\\EVAPORA\\" (car xestac2) ".CLI")))
      (SETQ FF2 (vl-file-size (STRCAT RUTA "bases de datos\\datos climatologicos\\clicom\\GRANIZO\\" (car xestac2) ".CLI")))
      (SETQ FF3 (vl-file-size (STRCAT RUTA "bases de datos\\datos climatologicos\\clicom\\HP\\" (car xestac2) ".CLI")))
      (SETQ FF4 (vl-file-size (STRCAT RUTA "bases de datos\\datos climatologicos\\clicom\\NEBLINA\\" (car xestac2) ".CLI")))
      (SETQ FF5 (vl-file-size (STRCAT RUTA "bases de datos\\datos climatologicos\\clicom\\NUBLADO\\" (car xestac2) ".CLI")))
      (SETQ FF6 (vl-file-size (STRCAT RUTA "bases de datos\\datos climatologicos\\clicom\\RAYOS\\" (car xestac2) ".CLI")))
      (SETQ FF7 (vl-file-size (STRCAT RUTA "bases de datos\\datos climatologicos\\clicom\\TEMP\\" (car xestac2) ".CLI")))
      (SETQ FF8 (vl-file-size (STRCAT RUTA "bases de datos\\datos climatologicos\\clicom\\TEMPMAX\\" (car xestac2) ".CLI")))
      (SETQ FF9 (vl-file-size (STRCAT RUTA "bases de datos\\datos climatologicos\\clicom\\TEMPMIN\\" (car xestac2) ".CLI")))
      (IF (/= FF1 NIL) (mode_tile "gevap" 0) (mode_tile "gevap" 1))
      (IF (/= FF2 NIL) (mode_tile "ggra" 0) (mode_tile "ggra" 1))
      (IF (/= FF3 NIL) (mode_tile "ghp" 0) (mode_tile "ghp" 1))
      (IF (/= FF4 NIL) (mode_tile "gneb" 0) (mode_tile "gneb" 1))
      (IF (/= FF5 NIL) (mode_tile "gnub" 0) (mode_tile "gnub" 1))
      (IF (/= FF6 NIL) (mode_tile "gray" 0) (mode_tile "gray" 1))
      (IF (/= FF7 NIL) (mode_tile "gtemp" 0) (mode_tile "gtemp" 1))
      (IF (/= FF8 NIL) (mode_tile "gtmax" 0) (mode_tile "gtmax" 1))
      (IF (/= FF9 NIL) (mode_tile "gtmin" 0) (mode_tile "gtmin" 1))
    )
  )
  (if (= procedencia "ERIC")
    (progn
      (mode_tile "gevap" 1)
      (mode_tile "ggra" 1)
      (mode_tile "ghp" 1)
      (mode_tile "gneb" 1)
      (mode_tile "gnub" 1)
      (mode_tile "gray" 1)
      (mode_tile "gtemp" 1)
      (mode_tile "gtmax" 1)
      (mode_tile "gtmin" 1)
    )
  )
)

(defun picaste (x y)
  (SETQ MOUSE (BUSACC LISTADCLOBJ X Y))
 ; (alert (ITOA X))
  (if (and (> X 545)(< X 550)(> Y 48)(< Y 58))(SETQ MOUSE "opft"))
  ;(Alert MOUSE)
  (if (= MOUSE "DIBUJO")
    (progn
      (setq kx x)
      (setq ky y)
      (DESTA vzoom)
      (setq x kx)
      (setq y ky)
      (setq dstx 1000000)
      (setq num2x 0)
      (if (= eclicom "1")
        (progn
          (SETQ IDESTx 1)
          (setq idestx (cdr (assoc num2x MATRIZEST)))
          (while idestx
            (SETQ pX (ATOI (RTOS (CAR idestx) 2 0)))
            (SETQ pY (ATOI (RTOS (CADR idestx) 2 0)))
            (setq distx (distance (list x y) (list px py)))
            (if (< distx dstx)
	      (progn
                (setq dstx distx)
                (setq nest (1+ num2x))
              )      
            )
            (setq num2x (1+ num2x))
            (setq idestx (cdr (assoc num2x MATRIZEST)))
          )
        )
      )
      (setq num3x 0) 
      (if (= eeric "1")
        (progn
          (SETQ IDESTx 1)
          (setq idestx (cdr (assoc num3x MATRIZEST2)))
          (while idestx
            (SETQ pX (ATOI (RTOS (CAR idestx) 2 0)))
            (SETQ pY (ATOI (RTOS (CADR idestx) 2 0)))
            (setq distx (distance (list x y) (list (- px 5) py)))
            (if (< distx dstx)
	      (progn
                (setq dstx distx)
                (setq nest (+ num2 num3x 1));estaciones2 estaciones
              )      
            )
            (setq num3x (1+ num3x))
            (setq idestx (cdr (assoc num3x MATRIZEST2)))
          )    
        )
      )
     ; (if (= eclicom "0")(setq nest(- nest nestclicom)))Quitar esta linea en la original
     (dpuntero vzoom)
    )
  )
  (IF (= MOUSE "opf") 
    (progn
      (if (= (estdefinitiva nest) "S")
        (progn
          (estdefinitivab nest)
          (start_image "imagen")
          (fill_image 13 431 7 7 0)
          (end_image)
        )
        (progn
          (if (or(> nest nestclicom)(/= eclicom "1"))
	    (progn
	    (if (or(/= eclicom "1")(= nestclicom 0))
            (setq ESTACFINALE (strcat ESTACFINALE (ntocad nest 0 5)))
	    (setq ESTACFINALE (strcat ESTACFINALE (ntocad (- nest(length MATRIZEST))0 5)))
	     )
	    )
            (setq ESTACFINALC (strcat ESTACFINALC (ntocad nest 0 5)))
          )
          (start_image "imagen")
          (fill_image 13 431 7 7 20)
          (end_image)
        )
      )
    )
  )
  (IF (= MOUSE "opft")
    (progn
     (set cuever 0)
     (setq verpol (cdr (assoc cuever estaciones)))
       (while verpol
	 (setq nest cuever)
         (if (= estdefinitiva  "S")
           (progn
            (estdefinitivab cuever)
            (start_image "imagen")
            (fill_image 13 431 7 7 0)
            (end_image)
           )
          (progn
            (if (or(> nest nestclicom)(/= eclicom "1"))
	     (progn
	      (if (/= eclicom "1")
              (setq ESTACFINALE (strcat ESTACFINALE (ntocad nest 0 5)))
	      (setq ESTACFINALE (strcat ESTACFINALE (ntocad (- nest(length MATRIZEST))0 5)))
	      )
	     )
             (setq ESTACFINALC (strcat ESTACFINALC (ntocad nest 0 5)))
            )
          (start_image "imagen")
          (fill_image 13 421 7 7 20)
          (end_image)
          )
	 )
     (set cuever (1+ cuever))
    (setq verpol (cdr (assoc cuever estaciones)))
     )
     (set cuever 0)
     (setq verpol (cdr (assoc cueve2r estaciones2)))
       (while verpol
	 (setq nest (+ cuever nestclicom))
         (if (= estdefinitiva  "S")
           (progn
            (estdefinitivab cuever2)
            (start_image "imagen")
            (fill_image 13 431 7 7 0)
            (end_image)
           )
          (progn
            (if (or(> nest nestclicom)(/= eclicom "1"))
	     (progn
	      (if (/= eclicom "1")
              (setq ESTACFINALE (strcat ESTACFINALE (ntocad nest 0 5)))
	      (setq ESTACFINALE (strcat ESTACFINALE (ntocad (- nest(length MATRIZEST))0 5)))
	      )
	     )
             (setq ESTACFINALC (strcat ESTACFINALC (ntocad nest 0 5)))
            )
          (start_image "imagen")
          (fill_image 13 421 7 7 20)
          (end_image)
          )
	 )
     (set cuever (1+ cuever))
    (setq verpol (cdr (assoc cuever estaciones)))
     )
   )
  )
  (IF (= (SUBSTR MOUSE 1 1) "G") 
    (progn
      (if (= mouse "GEVAPORA1") (setq varprv 1))
      (if (= mouse "GGRANIZO") (setq varprv 2))
      (if (= mouse "GPRECIPITACION") (setq varprv 3))
      (if (= mouse "GNIEBLA") (setq varprv 4))
      (if (= mouse "GNUBLADOS") (setq varprv 5))
      (if (= mouse "GTELECT") (setq varprv 6))
      (if (= mouse "GTEMP") (setq varprv 7))
      (if (= mouse "GTEMPMIN") (setq varprv 8))
      (if (= mouse "GTEMPMAX") (setq varprv 9))
      (setq numeroindicet "001")
      (if (not (encuentran varprv DATCLIMASOBRE)) (setq DATCLIMASOBRE (itoa varprv)))
      (setq DIALOGOGRF (strcat (substr DIALOGOGRF 1 10) "000000000" ))
      (setq DIALOGOGRF (strcat (substr DIALOGOGRF 1 (+ 10 (1- varprv))) "1" (substr DIALOGOGRF (+ 11 varprv))))
      (setq datoclimagrf varprv)
      (dibujaDCLGRF)
      (desactiva "mapa")
      (desactiva "opf")
      (desactiva "fb")
    )
  )
  (IF (= MOUSE "CERRARGRF") 
    (progn
       (SETQ VARPRV (SUBSTR DIALOGOGRF 2 1))
       (IF (= (SUBSTR DIALOGOGRF 1 1) "0")
         (progn
           (IF (= varprv "1")
             (desactiva "cr01")
           )
           (IF (= varprv "2")
             (desactiva "cr02")
           )
         )
         (progn
           (IF (= varprv "1")
             (desactiva "cr06")
           )
           (IF (= varprv "2")
             (desactiva "cr07")
           )
         )
       )
       (IF (= varprv "3")
          (desactiva "cr03")
       )
       (IF (= varprv "4")
         (desactiva "cr04")
       )
       (IF (= varprv "5")
         (PROGN
           (desactiva "cr05")
           (desactiva "cr051")
           (desactiva "cr052")
         )
       )
      (desactiva "pesta")
      (IF (= (SUBSTR DIALOGOGRF 1 1) "0")
        (desactiva "bp01")
        (desactiva "bp11")
      )
      (ACTIVA "control")
      (DESACTIVA "INDICES")
      (start_image "imagen")
      (activa "mapa")
      (activa "opf")
      (slide_image 6 5 147 159 (STRCAT RUTA "SLIDES\\9datos.SLD"))
      (fill_image 0 0 147 523 0)
      (end_image)
      (SETQ LISTADCLOBJ (MBDDCL LISTADCLOBJ "B" 0 0 0 0 "CERRARGRF"))
      (SETQ LISTADCLOBJ (MBDDCL LISTADCLOBJ "B" 0 0 0 0 "ACTUALIZAGRF"))
      (DIBUJO)
     ; (activa "fb")
     ; (activa "gb")
    )
  )
  (IF (= mouse "ACTUALIZAGRF")
    (progn
      (start_image "imagen")
      (fill_image 185 88 645 333 0)
      (fill_image 274 73 440 30 0)
      (rgrafica)
      (end_image)
    )
  )
  (IF (= mouse "TXT0")
    (progn
      (desactiva "cr06")
      (desactiva "cr07")
      (start_image "imagen")  
      (LIMPIA "bp11")
      (LIMPIA "cr05")
      (slide_image 179 2 660 41 (STRCAT RUTA "SLIDES\\PESTAŃA0.SLD"))
      (activa "bp01")
      (end_image)
      (setq DIALOGOGRF (strcat "0" (substr DIALOGOGRF 2 29)))
    )
  ) 
  (IF (= mouse "TXT1")
    (progn
      (desactiva "cr01")
      (desactiva "cr02")
      (desactiva "cr03")
      (desactiva "cr04")
      (desactiva "cr051")
      (desactiva "cr052")
      (start_image "imagen")  
      (LIMPIA "bp01")
      (LIMPIA "cr05")
      (slide_image 179 2 660 41 (STRCAT RUTA "SLIDES\\PESTAŃA1.SLD"))
      (activa "bp11")
      (end_image)
      (setq DIALOGOGRF (strcat "1" (substr DIALOGOGRF 2 29)))
    )
  )  
  (IF (= (SUBSTR MOUSE 1 2) "CR")
    (progn
       (SETQ VARPRV (SUBSTR DIALOGOGRF 2 1))
       (if (or (= mouse "CR025") (= mouse "CR026") (= mouse "CR027") (= mouse "CR028") (= mouse "CR029") (= mouse "CR030") (= mouse "CR031") (= mouse "CR032") (= mouse "CR033"))
         (PROGN
           (setq varprv (- (atoi (substr mouse 4 2)) 24))
           (if (/= DATCLIMASOBRE "")
             (if (not (encuentran varprv DATCLIMASOBRE))
               (progn
                 (if (or (and (or (= varprv 7) (= varprv 8) (= varprv 9)) (or (encuentran 7 DATCLIMASOBRE) (encuentran 8 DATCLIMASOBRE) (encuentran 9 DATCLIMASOBRE))) (and (or (= varprv 2) (= varprv 4) (= varprv 5) (= varprv 6)) (or (encuentran 2 DATCLIMASOBRE) (encuentran 4 DATCLIMASOBRE) (encuentran 5 DATCLIMASOBRE) (encuentran 6 DATCLIMASOBRE))) (and (or (= varprv 1) (= varprv 3)) (or (encuentran 1 DATCLIMASOBRE) (encuentran 3 DATCLIMASOBRE))))
                   (progn
                     (if (and (or (= varprv 1) (= varprv 3)) (or (encuentran 1 DATCLIMASOBRE) (encuentran 3 DATCLIMASOBRE)))
                        (setq DATCLIMASOBRE (strcat DATCLIMASOBRE (itoa varprv)))
                     ) 
                     (if (and (or (= varprv 2) (= varprv 4) (= varprv 5) (= varprv 6)) (or (encuentran 2 DATCLIMASOBRE) (encuentran 4 DATCLIMASOBRE) (encuentran 5 DATCLIMASOBRE) (encuentran 6 DATCLIMASOBRE)))
                        (setq DATCLIMASOBRE (strcat DATCLIMASOBRE (itoa varprv)))
                     ) 
                     (if (and (or (= varprv 7) (= varprv 8) (= varprv 9)) (or (encuentran 7 DATCLIMASOBRE) (encuentran 8 DATCLIMASOBRE) (encuentran 9 DATCLIMASOBRE)))
                        (setq DATCLIMASOBRE (strcat DATCLIMASOBRE (itoa varprv)))
                     )
                   )
                   (progn
                     (borrabtn DATCLIMASOBRE)
                     (setq DATCLIMASOBRE (itoa varprv))
                   ) 
                 )
               )
             )
             (progn
               (setq DATCLIMASOBRE (itoa varprv))
             )
           )
           (start_image "imagen")
           (fill_image 9 (+ 28 (* 16 (1- varprv))) 7 7 20)
           (end_image)
         )
       )
       (if (or (= mouse "CR01") (= mouse "CR02") (= mouse "CR03") (= mouse "CR04") (= mouse "CR05") (= mouse "CR06") (= mouse "CR07") (= mouse "CR08") (= mouse "CR09") (= mouse "CR010") (= mouse "CR011") (= mouse "CR012") (= mouse "CR013") (= mouse "CR014") (= mouse "CR015")) ; (= mouse "CR016") (= mouse "CR036")
         (progn
          (if (or  (= varprv "1") (= varprv "2") (= varprv "3"))
            (progn
               (if (= mouse "CR01") 
                 (if (/= (substr DIALOGOGRF 4 1) "6")
                   (SETQ DIALOGOGRF (strcat (substr DIALOGOGRF 1 3) "6" (substr DIALOGOGRF 5)))                   
                 )
               )
               (if (= mouse "CR03") 
                 (if (= (substr DIALOGOGRF 5 1) "5")
                   (SETQ DIALOGOGRF (strcat (substr DIALOGOGRF 1 4) "1" (substr DIALOGOGRF 6)))                   
                 )
               )
               (start_image "imagen") 
               (fill_image 6 (+ 26 (* (1- (atoi (SUBSTR DIALOGOGRF (+ 2 (atoi varprv)) 1))) 16)) 12 12 0)
               (slide_image 6 (+ 26 (* (1- (atoi (SUBSTR DIALOGOGRF (+ 2 (atoi varprv)) 1))) 16)) 12 12 (STRCAT RUTA "SLIDES\\c1.SLD"))
               (if (or (= mouse "CR01") (= mouse "CR02") (= mouse "CR03") (= mouse "CR04"))
                 (setq valorcr (SUBSTR MOUSE 4 1))
               )
               (if (or (= mouse "CR05") (= mouse "CR06") (= mouse "CR07") (= mouse "CR08") (= mouse "CR09"))
                 (setq valorcr (itoa (- (atoi (SUBSTR MOUSE 3 2)) 4)))
               )
               (if (= mouse "CR010")
                 (setq valorcr (itoa (- (atoi (SUBSTR MOUSE 4 2)) 4)))
               )
               (if (or (= mouse "CR011") (= mouse "CR012") (= mouse "CR013") (= mouse "CR014") (= mouse "CR015")) ;(= mouse "CR016")
                 (setq valorcr (itoa (- (atoi (SUBSTR MOUSE 4 2)) 10)))
               )
               (setq DIALOGOGRF (strcat (substr DIALOGOGRF 1 (+ 1 (atoi varprv))) valorcr (substr DIALOGOGRF (+ 3 (atoi varprv)))))
               (slide_image 6 (+ 26 (* (1- (atoi (SUBSTR DIALOGOGRF (+ 2 (atoi varprv)) 1))) 16)) 12 12 (STRCAT RUTA "SLIDES\\c2.SLD"))
               (end_image)
             )
           )
         )
       ) 
       (if (= varprv "4")
         (progn
            (start_image "imagen") 
            (if (= (SUBSTR DIALOGOGRF 6 1) "1")
              (progn
                (fill_image 35 41 68 30 0)
                (slide_image 35 41 68 30 (STRCAT RUTA "SLIDES\\BOTONESOPGRF(BT1)"))
              )
            )
            (if (= (SUBSTR DIALOGOGRF 6 1) "2")
              (progn
                (fill_image  35 74 68 30 0)
                (slide_image 35 74 68 30 (STRCAT RUTA "SLIDES\\BOTONESOPGRF(BT2)"))
              )
            )
            (if (= (SUBSTR DIALOGOGRF 6 1) "3")
              (progn
                (fill_image  35 107 68 30 0)
                (slide_image 35 107 68 30 (STRCAT RUTA "SLIDES\\BOTONESOPGRF(BT3)"))
              )
            )
           (if (= mouse "CR017")
             (slide_image 35 41 68 30 (STRCAT RUTA "SLIDES\\BOTONESOPGRF(BTP1)"))
           )
           (if (= mouse "CR018")
             (slide_image 35 74 68 30 (STRCAT RUTA "SLIDES\\BOTONESOPGRF(BTP2)"))
           )
           (if (= mouse "CR019")
             (slide_image 35 107 68 30 (STRCAT RUTA "SLIDES\\BOTONESOPGRF(BTP3)"))
           )
           (end_image)
           (setq DIALOGOGRF (strcat (substr DIALOGOGRF 1 5) (itoa (- (atoi (SUBSTR mouse 5 1)) 6)) (substr DIALOGOGRF 7)))
         )
       )
       (if (= varprv "5")
         (progn
           (if (or (= mouse "CR020") (= mouse "CR021"))
             (progn
               (start_image "imagen") 
               (if (= (SUBSTR DIALOGOGRF 7 1) "1")
                 (progn 
                   (fill_image 20 27 56 25 0)
                   (fill_image 6 64 164 186 0)
                   (slide_image 20 27 56 25 (STRCAT RUTA "SLIDES\\BOTONESOPGRF(BT4)"))
                   (desactiva "cr051")
                 )
               )
               (if (= (SUBSTR DIALOGOGRF 7 1) "2")
                 (progn 
                   (fill_image 91 27 56 25 0)
                   (fill_image 11 72 158 166 0)
                   (slide_image 91 27 56 25 (STRCAT RUTA "SLIDES\\BOTONESOPGRF(BT1)"))
                   (desactiva "cr052")
                 )
               )
               (if (= mouse "CR020")
                 (progn
                   (slide_image 20 27 56 25 (STRCAT RUTA "SLIDES\\BOTONESOPGRF(BTP4)"))
                   (slide_image 6 64 164 186 (STRCAT RUTA "SLIDES\\colores.SLD"))
                   (activa "cr051")
                 )
               )
               (if (= mouse "CR021")
                 (progn
                   (slide_image 91 27 56 25 (STRCAT RUTA "SLIDES\\BOTONESOPGRF(BTP1)"))
                   (slide_image 11 72 158 118 (STRCAT RUTA "SLIDES\\colores2.SLD"))
                   (slide_image 11 192 72 47 (STRCAT RUTA "SLIDES\\colores3.SLD"))
                   (activa "cr052")
                 )
               )
               (end_image)
               (setq DIALOGOGRF (strcat (substr DIALOGOGRF 1 6) (itoa (+ (atoi (SUBSTR mouse 5 1)) 1)) (substr DIALOGOGRF 8)))
             )
           )
           (if (= mouse "CR022")
             (progn
               (setq colorgrf (seccuad "001002003004005006007008009010011012013014015016017018019020021022023024025026027028029030031032033034035036037038039040041042043044045046047048049050051052053054055056057058059060061062063064065066067068069070071072073074075076077078079080081082083084085086087088089090091092093094095096097098099100101102103104105106107108109110111112113114115116117118119120121122123124125126127128129130131132133134135136137138139140141142143144145146147148149150151152153154155156157158159160161162163164165166167168169170171172173174175176177178179180181182183184185186187188189190191192193194195196197198199200201202203204205206207208209210211212213214215216217218219220221222223224225226227228229230231232233234235236237238239240241242243244245246247248249250251252253254255" 164.000 186.000 15 17 6 64 x y))
               (start_image "imagen") 
               (muestracl colorgrf 789 382 36 36)
               (dibujarect 787 380 826 419 20)
               (end_image)
             )
           );if
           (if (= mouse "CR023")
             (progn
               (setq colorx (seccuad "256257258259260261262263264265266267268269270271272273274275276277278279280281282283284285286287288289290291292293294295296297298299300301302303304305" 158.000 118.000 5 10 11 72 x y))
               (setq colorgrf (corrigecl colorx))
               (start_image "imagen") 
               (muestracl colorgrf 789 382 36 36)
               (dibujarect 787 380 826 419 20)
               (end_image)
             )
           );if
           (if (= mouse "CR024")
             (progn
               (setq colorx (seccuad "306307308309" 72.000 47.000 1 4 11 192 x y))
               (print colorx)
               (setq colorgrf (corrigecl colorx))
               (print colorgrf)
               (start_image "imagen") 
               (muestracl colorgrf 789 382 36 36)
               (dibujarect 787 380 826 419 20)
               (end_image)
             )
           );if
         )
       )  
    )
  )
  (IF (= MOUSE "INDICE1") 
    (PROGN
      (setq ACCION (seccuad "IND01IND02IND03IND04IND05IND06IND07IND08IND09IND10IND11IND12" 65 216 1 12 11 289 x y))
      (start_image "imagen") 
      (atzindice (substr fechainiex 1 4) (substr fechafinex 1 4) (substr ACCION 4 2))
      (end_image)
    )
  )
  (IF (= MOUSE "INDICE2") 
    (PROGN
      (setq ACCION (seccuad "IND201IND202IND203IND204IND205IND206IND207IND208IND209IND210IND211IND212IND213IND214IND215IND216IND217IND218IND219IND220" 76 180 2 10 87 307 x y))
      (ALERT ACCION)
    )
  )
  (IF (= (SUBSTR MOUSE 1 2) "BT") 
    (PROGN
       (start_image "imagen")  
       (SETQ VARPRV (SUBSTR DIALOGOGRF 2 1))
       (IF (= (SUBSTR DIALOGOGRF 1 1) "0")
         (progn
           (IF (= varprv "1")
             (LIMPIA "cr01")
           )
           (IF (= varprv "2")
             (LIMPIA "cr02")
           )
         )
         (progn
           (IF (= varprv "1")
             (LIMPIA "cr06")
           )
           (IF (= varprv "2")
             (LIMPIA "cr07")
           )
         )
       )
       (IF (= varprv "3")
          (LIMPIA "cr03")
       )
       (IF (= varprv "4")
         (LIMPIA "cr04")
       )
       (IF (= varprv "5")
         (PROGN
           (LIMPIA "cr05")
           (LIMPIA "cr051")
           (LIMPIA "cr052")
         )
       )
       (if (= MOUSE "BT01")
         (PROGN
           (fill_image 183 27 40 12 32) 
    	   (SETQ YVARIA 85)
           (activa "cr01")
         ) 
       )
       (if (= MOUSE "BT02")
         (PROGN
           (fill_image 230 27 72 12 32)
 	   (SETQ YVARIA 117)
           (activa "cr02")
           (controlgrf)
         )
       )
       (IF (= MOUSE "BT11")
         (PROGN
           (fill_image 183 27 78 12 32)
           (SETQ YVARIA 166)
           (activa "cr06")
         )
       )
       (IF (= MOUSE "BT12")
         (PROGN
           (fill_image 265 27 102 12 32)
           (SETQ YVARIA 265)
           (activa "cr07")
         )
       )
       (if (= MOUSE "BT03")
          (PROGN
            (fill_image 310 27 36 12 32)
	    (SETQ YVARIA 102)
            (activa "cr03")
            (controlgrf)
          )
       )
       (if (= MOUSE "BT04")
          (PROGN
            (fill_image 353 27 25 12 32)
	    (SETQ YVARIA 166)
            (if (= (SUBSTR DIALOGOGRF 6 1) "1")
              (progn 
                (slide_image 35 41 68 30 (STRCAT RUTA "SLIDES\\BOTONESOPGRF(BTP1)"))
                (slide_image 35 74 68 30 (STRCAT RUTA "SLIDES\\BOTONESOPGRF(BT2)"))
                (slide_image 35 107 68 30 (STRCAT RUTA "SLIDES\\BOTONESOPGRF(BT3)"))
              )
            )
            (if (= (SUBSTR DIALOGOGRF 6 1) "2")
              (progn 
                (slide_image 35 41 68 30 (STRCAT RUTA "SLIDES\\BOTONESOPGRF(BT1)"))
                (slide_image 35 74 68 30 (STRCAT RUTA "SLIDES\\BOTONESOPGRF(BTP2)"))
                (slide_image 35 107 68 30 (STRCAT RUTA "SLIDES\\BOTONESOPGRF(BT3)"))
              )
            )
            (if (= (SUBSTR DIALOGOGRF 6 1) "3")
              (progn 
                (slide_image 35 41 68 30 (STRCAT RUTA "SLIDES\\BOTONESOPGRF(BT1)"))
                (slide_image 35 74 68 30 (STRCAT RUTA "SLIDES\\BOTONESOPGRF(BT2)"))
                (slide_image 35 107 68 30 (STRCAT RUTA "SLIDES\\BOTONESOPGRF(BTP3)"))
              ) 
            )
            (activa "cr04")
          )
       )
       (if (= MOUSE "BT05")
          (PROGN
            (fill_image 386 27 49 12 32)
            (if (= (SUBSTR DIALOGOGRF 7 1) "1")
              (progn 
                (slide_image 20 27 56 25 (STRCAT RUTA "SLIDES\\BOTONESOPGRF(BTP4)"))
                (slide_image 91 27 56 25 (STRCAT RUTA "SLIDES\\BOTONESOPGRF(BT1)"))
                (slide_image 6 64 164 186 (STRCAT RUTA "SLIDES\\colores.SLD"))
                (activa "cr051")
              )
            )
            (if (= (SUBSTR DIALOGOGRF 7 1) "2")
              (progn 
                (slide_image 20 27 56 25 (STRCAT RUTA "SLIDES\\BOTONESOPGRF(BT4)"))
                (slide_image 91 27 56 25 (STRCAT RUTA "SLIDES\\BOTONESOPGRF(BTP1)"))
                (slide_image 11 72 158 118 (STRCAT RUTA "SLIDES\\colores2.SLD"))
                (slide_image 11 192 72 47 (STRCAT RUTA "SLIDES\\colores3.SLD"))
                (activa "cr052")
              )
            )
	    (SETQ YVARIA 265)
            (activa "cr05")
          )
       )
       (if (or (= MOUSE "BT01") (= MOUSE "BT02") (= MOUSE "BT03") (= MOUSE "BT04") (= MOUSE "BT05"))
         (progn
           (slide_image 179 2 660 41 (STRCAT RUTA "SLIDES\\PESTAŃA0.SLD"))
           (slide_image 3 3 173 YVARIA (STRCAT RUTA "SLIDES\\PESTAŃA0" (SUBSTR mouse 4 1) ".SLD")) 
         )
         (progn
           (slide_image 179 2 660 41 (STRCAT RUTA "SLIDES\\PESTAŃA1.SLD"))
           (slide_image 3 3 173 YVARIA (STRCAT RUTA "SLIDES\\PESTAŃA1" (SUBSTR mouse 4 1) ".SLD")) 
         )
       )
       (if (or (= MOUSE "BT01") (= MOUSE "BT02") (= MOUSE "BT03"))
         (slide_image 6 (+ 26 (* (1- (atoi (SUBSTR DIALOGOGRF (+ 2 (atoi (SUBSTR mouse 4 1))) 1))) 16)) 12 12 (STRCAT RUTA "SLIDES\\c2.SLD"))
       )
       (IF (= MOUSE "BT11")
          (dibubtn DATCLIMASOBRE)
       )
       (setq DIALOGOGRF (strcat (substr DIALOGOGRF 1 1) (SUBSTR mouse 4 1) (substr DIALOGOGRF 3 28)))
       (end_image) 
    )
  )
)

(defun corrigecl (color)
  (if (< (atoi color) 280)
    (progn
      (setq nbase (+ 10 (* 10 (- (atoi color) 256))))
      (setq colorf (strcat (ntocad nbase 0 3) (ntocad (+ nbase 2) 0 3) (ntocad (+ nbase 4) 0 3) (ntocad (+ nbase 6) 0 3) (ntocad (+ nbase 8) 0 3)))
    )
  )
  (if (and (> (atoi color) 279) (< (atoi color) 304))
    (progn
      (setq nbase (+ 11 (* 10 (- (atoi color) 280))))
      (setq colorf (strcat (ntocad nbase 0 3) (ntocad (+ nbase 2) 0 3) (ntocad (+ nbase 4) 0 3) (ntocad (+ nbase 6) 0 3) (ntocad (+ nbase 8) 0 3)))
    )
  )
  (if (= color "304")(setq colorf "251252253254255"))
  (if (= color "306")(setq colorf "007131141140142152154164166176178"))
  (if (= color "307")(setq colorf "051041040030032022024014016018"))
  (if (= color "308")(setq colorf "007241231221211201191190192194196198"))
  (if (= color "309")(setq colorf "007051041040042044046048"))
  (setq colorf colorf)
)

(defun borrabtn (cadena)
  (setq nciclos (strlen cadena))
  (setq conten 1)
  (setq resultado nil)
  (start_image "imagen")
  (repeat nciclos
    (fill_image 9 (+ 28 (* 16 (1- (atoi (substr cadena conten 1))))) 7 7 0)
    (setq conten (1+ conten))
  )
  (end_image)
)

(defun dibubtn (cadena)
  (setq nciclos (strlen cadena))
  (setq conten 1)
  (repeat nciclos
    (fill_image 9 (+ 28 (* 16 (1- (atoi (substr cadena conten 1))))) 7 7 20)
    (setq conten (1+ conten))
  )
)

(defun encuentran (numero cadena)
  (setq nciclos (strlen cadena))
  (setq conten 1)
  (setq resultado nil)
  (repeat nciclos
    (if (= (atoi (substr cadena conten 1)) numero)
      (setq resultado T)
    )
    (setq conten (1+ conten))
  )
  (setq resultado resultado)
)

(defun dibujaDCLGRF ()
  (activa "pesta")
  (ACTIVA "INDICES")
  (ACTIVA "control")
  (start_image "imagen")
  (fill_image 0 0 918 524 0)
  (SETQ LISTADCLOBJ (MBDDCL LISTADCLOBJ "A" 798 54 836 86 "CERRARGRF"))
  (SETQ LISTADCLOBJ (MBDDCL LISTADCLOBJ "A" 760 54 836 86 "ACTUALIZAGRF"))
  (slide_image 798 54 32 32 (STRCAT RUTA "SLIDES\\CERRAR.SLD"))
  (slide_image 760 54 32 32 (STRCAT RUTA "SLIDES\\ACTUALIZA.SLD"))
  (dibujaPESTA)
  (slide_image 179 49 660 434 (STRCAT RUTA "SLIDES\\GRF(dtgrf)"))
  (slide_image 485 482 143 40 (STRCAT RUTA "SLIDES\\avance.SLD"))
  (rgrafica)
  (end_image)
)

(defun conviertevar (cadena)
  (setq anresta (atoi (substr cadena 1 4)))
  (setq anfin (atoi (substr cadena 7 4)))
  (setq contk 0)
  (setq cadenaxf "")
  (repeat (- anfin anresta)
    (setq varprv (substr cadena (+ 22 (* contk 9))))
    (setq varprv1 (substr varprv 1 4))
    (setq varprv2 (substr varprv 5 5))
    (setq varprv1 (ntocad (- (atoi varprv1) anresta) 0 3))
    (setq cadenaxf (strcat cadenaxf varprv1 varprv2))
    (setq contk (1+ contk))
  )
  (setq cadenaxf cadenaxf)
)

(defun rgrafica ()
  (if (= "1" (substr DIALOGOGRF 6 1)) (setq tipogrf "BR"))
  (if (= "2" (substr DIALOGOGRF 6 1)) (setq tipogrf "LI"))
  (if (= "3" (substr DIALOGOGRF 6 1)) (setq tipogrf "DS"))
  (if (= "1" (substr DIALOGOGRF 3 1)) (setq tipodatf "AN"))
  (if (= "2" (substr DIALOGOGRF 3 1)) (setq tipodatf "ME"))
  (if (= "3" (substr DIALOGOGRF 3 1)) (setq tipodatf "MM"))
  (if (= "4" (substr DIALOGOGRF 3 1)) (setq tipodatf "ST"))
  (if (= "1" (substr DIALOGOGRF 5 1)) (setq tipoPROf "MA"))
  (if (= "2" (substr DIALOGOGRF 5 1)) (setq tipoPROf "ME"))
  (if (= "3" (substr DIALOGOGRF 5 1)) (setq tipoPROf "MI"))
  (if (= "4" (substr DIALOGOGRF 5 1)) (setq tipoPROf "TO"))
  (if (= "5" (substr DIALOGOGRF 5 1)) (setq tipoPROf "VC"))
  (setq datoclimagrf (atoi (substr DATCLIMASOBRE 1 1)))
  (if (and (OR (= datoclimagrf 3) (= datoclimagrf 1)) (= tipoPROf "TO") (= tipodatf "AN")) (progn (setq hini 0) (setq hfin 3000)))          
  (if (and (OR (= datoclimagrf 3) (= datoclimagrf 1)) (= tipoPROf "TO") (= tipodatf "ME")) (progn (setq hini 0) (setq hfin 400))) 
  (if (and (OR (= datoclimagrf 3) (= datoclimagrf 1)) (OR (= tipoPROf "ME") (= tipoPROf "MA") (= tipoPROf "MI")) (OR (= tipodatf "ME") (= tipodatf "AN"))) (progn (setq hini 0) (setq hfin 30)))
  (if (and (= datoclimagrf 3) (= tipoPROf "MA") (OR (= tipodatf "ME") (= tipodatf "AN"))) (progn (setq hini 0) (setq hfin 90)))
  (if (and (OR (= datoclimagrf 7) (= datoclimagrf 8) (= datoclimagrf 9)) (= tipoPROf "TO") (= tipodatf "AN")) (progn (setq hini 0) (setq hfin 15000)))          
  (if (and (OR (= datoclimagrf 7) (= datoclimagrf 8) (= datoclimagrf 9)) (= tipoPROf "TO") (= tipodatf "ME")) (progn (setq hini 0) (setq hfin 1500))) 
  (if (and (OR (= datoclimagrf 7) (= datoclimagrf 8) (= datoclimagrf 9)) (OR (= tipoPROf "ME") (= tipoPROf "MA") (= tipoPROf "MI")) (OR (= tipodatf "ME") (= tipodatf "AN"))) (progn (setq hini -10) (setq hfin 50)))
  (if (and (OR (= datoclimagrf 2) (= datoclimagrf 4) (= datoclimagrf 5) (= datoclimagrf 6)) (= tipoPROf "TO") (= tipodatf "AN")) (progn (setq hini 0) (setq hfin 400)))          
  (if (and (OR (= datoclimagrf 2) (= datoclimagrf 4) (= datoclimagrf 5) (= datoclimagrf 6)) (= tipoPROf "TO") (= tipodatf "ME")) (progn (setq hini 0) (setq hfin 40)))          
  (if (and (OR (= datoclimagrf 2) (= datoclimagrf 4) (= datoclimagrf 5) (= datoclimagrf 6)) (AND (/= tipoPROf "TO") (/= tipoPROf "VC")) (OR (= tipodatf "ME") (= tipodatf "AN"))) (progn (setq hini 0) (setq hfin 2)))          
  (IF (= tipoPROf "VC") (progn (setq hini 0) (setq hfin 100)))
  (setq nestach nest)
  (if (> nestach nestclicom)
    (setq ldatex (cdr (assoc (- nestach nestclicom) matrizporcentaje)))
    (setq ldatex (cdr (assoc nestach matrizporcentajc)))
  )
  (setq ldatex (cdr (assoc datoclimagrf ldatex)))
  (setq fechainiex (substr ldatex 1 6));cambio de 6 a 4
  (setq fechafinex (substr ldatex 7 6))
  (setq fechainiex(itoa(-(atoi fechainiex) 100)))
  (setq fechainiex2 fechainiex)
  (setq fechafinex2 fechafinex)
  
  (if (= tipodatf "ST") 
    (progn
      (setq fechafinex2 (strcat (itoa (+ (atoi numeroindicet) (atoi (substr fechainiex 1 4)))) (substr fechainiex 5 2)))
      (setq fechainiex2 (strcat (itoa (+ (1- (atoi numeroindicet)) (atoi (substr fechainiex 1 4)))) (substr fechainiex 5 2)))
    )
  )
  (dibujaindicea (substr fechainiex 1 4) (substr fechafinex 1 4))
  (graficaestac (car (nestacc2 nestach)) (substr procedencia 1 1) datoclimagrf "A" "S" "S" colorgrf tipogrf fechainiex2 fechafinex2 hini hfin tipodatf tipoPROf)
  (setq nciclos (1- (strlen DATCLIMASOBRE)))
  (setq conten 2)
  (repeat nciclos
    (if (= (strlen colorgrf) 3)
      (if (< 253 (atoi colorgrf)) (setq colorgrf (ntocad (- (atoi colorgrf) (* 2 (1- conten))) 0 3)) (setq colorgrf (ntocad (+ (atoi colorgrf) (* 2 (1- conten))) 0 3))) 
    )
    (graficaestac (car (nestacc2 nestach)) (substr procedencia 1 1) (atoi (substr DATCLIMASOBRE conten 1)) "A" "N" "N" colorgrf tipogrf fechainiex2 fechafinex2 hini hfin tipodatf tipoPROf)
    (setq conten (1+ conten))
  )
  (muestracl colorgrf 789 382 36 36)
  (dibujarect 787 380 826 419 20)
)

(defun Ielevacion (ESTACION)
  (if (= procedencia "CLICOM")
    (progn
      (setq contcig 1)
      (setq estaciong (substr bdmemclicom 1 58))
      (while (and (/= estacion (vl-string-trim " " (substr estaciong 1 5))) (< (1- contcig) (/ (strlen indiceclicom) 6)))
        (setq estaciong (substr bdmemclicom (+ 1 (* (1- (atoi (substr indiceclicom (1+ (* (1- contcig) 6)) 6))) 58)) 58))
        (setq contcig (1+ contcig))
      )
      (setq denominacionv (vl-string-trim " " (substr estaciong 55 4)))
    )
    (progn
      (setq contcig 1)
      (setq estaciong (substr bdmemeric 1 58))
      (while (and (/= estacion (vl-string-trim " " (substr estaciong 1 5))) (< (1- contcig) (/ (strlen indiceeric) 6)))
        (setq estaciong (substr bdmemeric (+ 1 (* (1- (atoi (substr indiceeric (1+ (* (1- contcig) 6)) 6))) 58)) 58))
        (setq contcig (1+ contcig))
      )
      (setq denominacionv (vl-string-trim " " (substr estaciong 55 4)))
    )
  )
  (setq denominacionv denominacionv)
)

(defun dibujaPESTA ()
  (SETQ COLORLDCL 4)
  (SETQ LISTADCLOBJ (MBDDCL LISTADCLOBJ "A" 812 1 836 20 "CERRARGRF"))
  (IF (= (SUBSTR DIALOGOGRF 1 1) "0")
    (PROGN
       (activa "bp01")
       (SETQ VARPRV (SUBSTR DIALOGOGRF 2 1))
       (IF (= VARPRV "1")
         (PROGN
           (fill_image 183 27 40 12 32)
	   (SETQ YVARIA 85)
           (activa "cr01")
         )
       )
       (IF (= VARPRV "2")
         (PROGN
           (fill_image 230 27 72 12 32)
	   (SETQ YVARIA 117)
           (activa "cr02")
         )
       )
       (IF (= VARPRV "3")
         (PROGN
           (fill_image 310 27 36 12 32)
	   (SETQ YVARIA 102)
           (activa "cr03")
         )
       )
       (IF (= VARPRV "4")
         (PROGN
           (fill_image 353 27 25 12 32)
	   (SETQ YVARIA 166)
           (if (= (SUBSTR DIALOGOGRF 6 1) "1")
             (progn 
               (slide_image 35 41 68 30 (STRCAT RUTA "SLIDES\\BOTONESOPGRF(BTP1)"))
               (slide_image 35 74 68 30 (STRCAT RUTA "SLIDES\\BOTONESOPGRF(BT2)"))
               (slide_image 35 107 68 30 (STRCAT RUTA "SLIDES\\BOTONESOPGRF(BT3)"))
             )
           )
           (if (= (SUBSTR DIALOGOGRF 6 1) "2")
             (progn 
               (slide_image 35 41 68 30 (STRCAT RUTA "SLIDES\\BOTONESOPGRF(BT1)"))
               (slide_image 35 74 68 30 (STRCAT RUTA "SLIDES\\BOTONESOPGRF(BTP2)"))
               (slide_image 35 107 68 30 (STRCAT RUTA "SLIDES\\BOTONESOPGRF(BT3)"))
             )
           )
           (if (= (SUBSTR DIALOGOGRF 6 1) "3")
             (progn 
               (slide_image 35 41 68 30 (STRCAT RUTA "SLIDES\\BOTONESOPGRF(BT1)"))
               (slide_image 35 74 68 30 (STRCAT RUTA "SLIDES\\BOTONESOPGRF(BT2)"))
               (slide_image 35 107 68 30 (STRCAT RUTA "SLIDES\\BOTONESOPGRF(BTP3)"))
             )
           )
           (activa "cr04")
         )
       )
       (IF (= VARPRV "5")
         (PROGN
           (fill_image 386 27 49 12 32)
           (if (= (SUBSTR DIALOGOGRF 7 1) "1")
             (progn 
               (slide_image 20 27 56 25 (STRCAT RUTA "SLIDES\\BOTONESOPGRF(BTP4)"))
               (slide_image 91 27 56 25 (STRCAT RUTA "SLIDES\\BOTONESOPGRF(BT1)"))
               (slide_image 6 64 164 186 (STRCAT RUTA "SLIDES\\colores.SLD"))
               (activa "cr051")
             )
           )
           (if (= (SUBSTR DIALOGOGRF 7 1) "2")
             (progn 
               (slide_image 20 27 56 25 (STRCAT RUTA "SLIDES\\BOTONESOPGRF(BT4)"))
               (slide_image 91 27 56 25 (STRCAT RUTA "SLIDES\\BOTONESOPGRF(BTP1)"))
               (slide_image 11 72 158 166 (STRCAT RUTA "SLIDES\\colores1.SLD"))
               (activa "cr052")
             )
           )
	   (SETQ YVARIA 265)
           (activa "cr05")
         )
       )
       (slide_image 179 2 660 41 (STRCAT RUTA "SLIDES\\PESTAŃA0.SLD"))
       (slide_image 3 3 173 YVARIA (STRCAT RUTA "SLIDES\\PESTAŃA0" (SUBSTR DIALOGOGRF 2 1) ".SLD"))
       (if (or (= varprv "1") (= varprv "2") (= varprv "3"))
         (slide_image 6 (+ 26 (* (1- (atoi (SUBSTR DIALOGOGRF (+ 2 (atoi varprv)) 1))) 16)) 12 12 (STRCAT RUTA "SLIDES\\c2.SLD"))
       )      
    )
  )
  (IF (= (SUBSTR DIALOGOGRF 1 1) "1")
    (PROGN
       (activa "bp11")
       (SETQ VARPRV (SUBSTR DIALOGOGRF 2 1))
       (IF (= VARPRV "1")
         (PROGN
           (fill_image 183 27 78 12 32)
	   (SETQ YVARIA 166)
           (activa "cr06")
         )
       )
       (IF (= VARPRV "2")
         (PROGN
           (fill_image 265 27 102 12 32)
	   (SETQ YVARIA 265)
           (activa "cr07")
         )
       )
       (slide_image 179 2 660 41 (STRCAT RUTA "SLIDES\\PESTAŃA1.SLD"))
       (slide_image 3 3 173 YVARIA (STRCAT RUTA "SLIDES\\PESTAŃA1" (SUBSTR DIALOGOGRF 2 1) ".SLD"))
    )
  )
)
(defun dibujabtn (x1 y1 x2 y2 texto)
  (dibujarect x1 y1 x2 y2 COLORLDCL)
  (stexto texto "romans" (- y2 y1 2) (+ x1 2) (+ y1 2))
)

(defun dibujarect (x1 y1 x2 y2 color)
  (vector_image x1 y1 x2 y1 color)
  (vector_image x1 y1 x1 y2 color)
  (vector_image x1 y2 x2 y2 color)
  (vector_image x2 y1 x2 y2 color)
)

(defun smiles (valor)
  (if (> valor 999999.9999)
    (progn 
      (setq millon (fix (/ valor 1000000)))
      (setq miles (fix (/ (- valor (* 1000000 millon)) 1000)))
      (setq resto (- valor (* 1000000 millon) (* 1000 miles)))
      (setq salida (strcat (itoa millon) "'" (itoa miles) "," (rtos resto 2 3)))
    )
  )
  (if (and (> valor 1000) (< valor 1000000))
    (progn 
      (setq miles (fix (/ valor 1000)))
      (setq resto (- valor (* 1000 miles)))
      (setq salida (strcat (itoa miles) "," (rtos resto 2 3)))
    )
  )
  (if (< valor 1000)
      (setq salida (rtos valor 2 3))
  )
  (setq salida salida)
)

(defun busca (gbmin gbmax)
  (SETQ CONTANIM 1)
  (setq nestclicom 0)
  (acet-ui-progress-init "Buscando estaciones:" 6063)
  (dos_waitcursor t)
  (SETQ ESTACIONES (ESTACLIC2 GbMIN GbMAX))
  (acet-ui-progress-done)
  (dos_waitcursor)
  (acet-ui-progress-init "Buscando estaciones:" 6063)
  (dos_waitcursor t)
  (SETQ ESTACIONES2 (ESTERIC GbMIN GbMAX))
  (acet-ui-progress-done)
  (dos_waitcursor)
)

(defun busca2 ()
  (setq dbus (atoi (get_tile "dbus")))
  (setq opbusqueda "b")
  (done_dialog)
)

(defun segundoprv ()
  (setq opbusqueda "s")
  (done_dialog)
)

(DEFUN ANIM ()
  (IF (= CONTANIM NIL) (SETQ CONTANIM 1))
  (acet-ui-progress-safe contanim)
  (SETQ CONTANIM (1+ CONTANIM))
)

(DEFUN ANIM2 ()
  (IF (= CONTANIM NIL) (SETQ CONTANIM 1))
  (dos_getprogress contanim)
  (SETQ CONTANIM (1+ CONTANIM))
)

(defun leyenbtn (nestac)
  (if (= eclicom "0")(setq nestac (+ nestac nestclicom)));///
  (if (> nestac nestclicom)
    (setq ldat (cdr (assoc (- nestac nestclicom) matrizporcentaje)))
    (setq ldat (cdr (assoc nestac matrizporcentajc)))
  )
  (setq fuentescr "romans")
  (setq tam1 20)
  (setq tam2 16)
  (setq contly 1)
  (fill_image 0 597 918 624 0)
  (repeat 9
    (setq datocl (cdr (assoc contly ldat)))
    (if (= datocl "XXXXX") (SETQ DATOCL "XXXXXXXXXXXXXXXXXXXXX"))
    (setq x1ly (+ 10 (* (1- contly) 100)))
    (setq x2ly (+ 70 (* (1- contly) 100)))
    (setq verpolly (strcat (substr datocl 13 5) "%"))
    (stexto verpolly fuentescr tam2 x1lY 595)
    (setq verpolly (strcat (substr datocl 1 4) "-" (substr datocl 7 4)))
    (stexto verpolly fuentescr tam2 x1lY 607)
    (setq verpolly (itoa (atoi (substr datocl 18 4))))
    (stexto verpolly fuentescr tam1 x2lY 592)
    (setq contly (1+ contly))
  )
)

(defun leyenbtnex (nestact)
  (if (= eclicom "0")(+ nestact nestclicom))
 (setq nestacc 1)
 (repeat nestact
  (if (> nestacc nestclicom)
    (setq ldat (cdr (assoc (- nestacc nestclicom) matrizporcentaje)))
    (setq ldat (cdr (assoc nestacc matrizporcentajc)))
  )
  (setq contly 3)
  (setq concentrado "")
    (setq datocl (cdr (assoc contly ldat)))
    (if (= datocl "XXXXXX") (SETQ DATOCL "XXXXXXXXXXXXXXXXXXXXX"))
    (setq x1ly (+ 10 (* (1- contly) 100)))
    (setq x2ly (+ 70 (* (1- contly) 100)))
    (setq verpolly (strcat (substr datocl 13 5) "%"))
    (setq concentrado (strcat concentrado verpolly))
    (setq verpolly (strcat (substr datocl 1 4) "-" (substr datocl 7 4)))
    (setq concentrado (strcat concentrado "," verpolly))
    (setq verpolly (itoa (atoi (substr datocl 18 4))))
    (setq concentrado (strcat concentrado "," verpolly))
    (print concentrado)
  (setq nestacc (1+ nestacc))
 )
)

(defun carga (objetos)
  (if (= objetos "gb")
    (progn
      (slide_image 10 531 95 65 (STRCAT RUTA "SLIDES\\bevap.SLD"))
      (slide_image 110 531 95 65 (STRCAT RUTA "SLIDES\\bgran.SLD"))
      (slide_image 210 531 95 65 (STRCAT RUTA "SLIDES\\bllu.SLD"))
      (slide_image 310 531 95 65 (STRCAT RUTA "SLIDES\\bneb.SLD"))
      (slide_image 410 531 95 65 (STRCAT RUTA "SLIDES\\bnub.SLD"))
      (slide_image 510 531 95 65 (STRCAT RUTA "SLIDES\\bray.SLD"))
      (slide_image 610 531 95 65 (STRCAT RUTA "SLIDES\\btem.SLD"))
      (slide_image 710 531 95 65 (STRCAT RUTA "SLIDES\\btmax.SLD"))
      (slide_image 810 531 95 65 (STRCAT RUTA "SLIDES\\btmin.SLD"))
      (activa "gb")
    )
  )
  (if (= objetos "fb")
    (progn
      (slide_image 6 5 147 159 (STRCAT RUTA "SLIDES\\9datos.SLD"))
      (activa "fb")
    )
  )
)

(defun limpia (objetos)
  (if (= objetos "opf")
    (progn
      (desactiva "opf")
      (fill_image 10 425 152 18 0)
    )
  )
  (if (= objetos "fb")
    (progn
      (desactiva "fb")
      (fill_image 6 5 147 159 0)
    )
  )
  (if (= objetos "pesta")
    (progn
      (desactiva "pesta")
      (fill_image 179 2 660 41 0)
    )
  )
  (if (= objetos "mapa")
    (progn
      (desactiva "mapa")
      (fill_image 100 0 818 524 0)
    )
  )
  (if (= objetos "bp01")
    (progn
      (desactiva "bp01")
      (fill_image 179 2 660 41 0)
    )
  )
  (if (= objetos "bp11")
    (progn
      (desactiva "bp11")
      (fill_image 179 2 660 41 0)
    )
  )
  (if (= objetos "cr01")
    (progn
      (desactiva "cr01")
      (fill_image 2 2 173 87 0)
      (fill_image 183 27 40 12 0)
    )
  )
  (if (= objetos "cr02")
    (progn
      (desactiva "cr02")
      (fill_image 2 2 173 119 0)
      (fill_image 230 27 72 12 0)
    )
  )
  (if (= objetos "cr03")
    (progn
      (desactiva "cr03")
      (fill_image 2 2 173 136 0)
      (fill_image 310 27 36 12 0)
    )
  )
  (if (= objetos "cr04")
    (progn
      (desactiva "cr04")
      (fill_image 2 2 173 168 0)
      (fill_image 353 27 25 12 0)
    )
  )
  (if (= objetos "cr05")
    (progn
      (desactiva "cr05")
      (fill_image 2 2 173 267 0)
      (fill_image 386 27 49 12 0)
    )
  )
  (if (= objetos "cr051")
    (progn
      (desactiva "cr051")
      (fill_image 6 64 164 188 0)
    )
  )
  (if (= objetos "cr052")
    (progn
      (desactiva "cr052")
      (fill_image 6 64 164 188 0)
    )
  )
  (if (= objetos "cr06")
    (progn
      (desactiva "cr06")
      (fill_image 2 2 173 168 0)
      (fill_image 183 27 78 12 0)
    )
  )
  (if (= objetos "cr07")
    (progn
      (desactiva "cr07")
      (fill_image 2 2 173 267 0)
      (fill_image 265 27 102 12 0)
    )
  )
)

(defun desactiva (objetos)
  (if (= objetos "opf")
    (SETQ LISTADCLOBJ (MBDDCL LISTADCLOBJ "B" 0 0 0 0 "opf"))
  )
  (if (= objetos "control")
    (progn
      (SETQ LISTADCLOBJ (MBDDCL LISTADCLOBJ "B" 0 0 0 0 "av1"))
      (SETQ LISTADCLOBJ (MBDDCL LISTADCLOBJ "B" 0 0 0 0 "av2"))
      (SETQ LISTADCLOBJ (MBDDCL LISTADCLOBJ "B" 0 0 0 0 "av3"))
      (SETQ LISTADCLOBJ (MBDDCL LISTADCLOBJ "B" 0 0 0 0 "av4"))
    )
  )
  (if (= objetos "INDICES")
    (progn
      (SETQ LISTADCLOBJ (MBDDCL LISTADCLOBJ "B" 0 0 0 0 "INDICE1"))
      (SETQ LISTADCLOBJ (MBDDCL LISTADCLOBJ "B" 0 0 0 0 "INDICE2"))
    )
  )
  (if (= objetos "gb")
    (progn
      (SETQ LISTADCLOBJ (MBDDCL LISTADCLOBJ "B" 0 0 0 0 "GEVAPORA1"))
      (SETQ LISTADCLOBJ (MBDDCL LISTADCLOBJ "B" 0 0 0 0 "GGRANIZO"))
      (SETQ LISTADCLOBJ (MBDDCL LISTADCLOBJ "B" 0 0 0 0 "GPRECIPITACION"))
      (sETQ LISTADCLOBJ (MBDDCL LISTADCLOBJ "B" 0 0 0 0 "GNIEBLA"))
      (SETQ LISTADCLOBJ (MBDDCL LISTADCLOBJ "B" 0 0 0 0 "GNUBLADOS"))
      (SETQ LISTADCLOBJ (MBDDCL LISTADCLOBJ "B" 0 0 0 0 "GTELECT"))
      (SETQ LISTADCLOBJ (MBDDCL LISTADCLOBJ "B" 0 0 0 0 "GTEMP"))
      (SETQ LISTADCLOBJ (MBDDCL LISTADCLOBJ "B" 0 0 0 0 "GTEMPMIN"))
      (SETQ LISTADCLOBJ (MBDDCL LISTADCLOBJ "B" 0 0 0 0 "GTEMPMAX"))
    )
  )
  (if (= objetos "fb")
    (progn
      (SETQ LISTADCLOBJ (MBDDCL LISTADCLOBJ "B" 0 0 0 0 "FGRANIZO"))
      (SETQ LISTADCLOBJ (MBDDCL LISTADCLOBJ "B" 0 0 0 0 "FPRECIPITACION"))
      (SETQ LISTADCLOBJ (MBDDCL LISTADCLOBJ "B" 0 0 0 0 "FNIEBLA"))
      (SETQ LISTADCLOBJ (MBDDCL LISTADCLOBJ "B" 0 0 0 0 "FNUBLADOS"))
      (SETQ LISTADCLOBJ (MBDDCL LISTADCLOBJ "B" 0 0 0 0 "FTELECTR"))
      (SETQ LISTADCLOBJ (MBDDCL LISTADCLOBJ "B" 0 0 0 0 "FTEMP"))
      (SETQ LISTADCLOBJ (MBDDCL LISTADCLOBJ "B" 0 0 0 0 "FTEMPMIN"))
      (SETQ LISTADCLOBJ (MBDDCL LISTADCLOBJ "B" 0 0 0 0 "FEVAPORA"))
      (SETQ LISTADCLOBJ (MBDDCL LISTADCLOBJ "B" 0 0 0 0 "FTEMPMAX"))
    )
  )
  (if (= objetos "pesta")
    (progn
      (SETQ LISTADCLOBJ (MBDDCL LISTADCLOBJ "B" 0 0 0 0 "TXT0"))
      (SETQ LISTADCLOBJ (MBDDCL LISTADCLOBJ "B" 0 0 0 0 "TXT1"))
    )
  )
  (if (= objetos "mapa")
    (SETQ LISTADCLOBJ (MBDDCL LISTADCLOBJ "B" 0 0 0 0 "DIBUJO"))
  )
  (if (= objetos "bp01")
    (progn
       (SETQ LISTADCLOBJ (MBDDCL LISTADCLOBJ "B" 0 0 0 0 "BT01"))
       (SETQ LISTADCLOBJ (MBDDCL LISTADCLOBJ "B" 0 0 0 0 "BT02"))
       (SETQ LISTADCLOBJ (MBDDCL LISTADCLOBJ "B" 0 0 0 0 "BT03"))
       (SETQ LISTADCLOBJ (MBDDCL LISTADCLOBJ "B" 0 0 0 0 "BT04"))
       (SETQ LISTADCLOBJ (MBDDCL LISTADCLOBJ "B" 0 0 0 0 "BT05"))
    )
  )
  (if (= objetos "bp11")
    (progn
       (SETQ LISTADCLOBJ (MBDDCL LISTADCLOBJ "B" 0 0 0 0 "BT11"))
       (SETQ LISTADCLOBJ (MBDDCL LISTADCLOBJ "B" 0 0 0 0 "BT12"))
    )
  )
  (if (= objetos "cr01")
    (progn
       (SETQ LISTADCLOBJ (MBDDCL LISTADCLOBJ "B" 0 0 0 0 "CR01"))
       (SETQ LISTADCLOBJ (MBDDCL LISTADCLOBJ "B" 0 0 0 0 "CR02"))
       (SETQ LISTADCLOBJ (MBDDCL LISTADCLOBJ "B" 0 0 0 0 "CR03"))
       (SETQ LISTADCLOBJ (MBDDCL LISTADCLOBJ "B" 0 0 0 0 "CR04"))
    )
  )
  (if (= objetos "cr02")
    (progn
       (SETQ LISTADCLOBJ (MBDDCL LISTADCLOBJ "B" 0 0 0 0 "CR05"))
       (SETQ LISTADCLOBJ (MBDDCL LISTADCLOBJ "B" 0 0 0 0 "CR06"))
       (SETQ LISTADCLOBJ (MBDDCL LISTADCLOBJ "B" 0 0 0 0 "CR07"))
       (SETQ LISTADCLOBJ (MBDDCL LISTADCLOBJ "B" 0 0 0 0 "CR08"))
       (SETQ LISTADCLOBJ (MBDDCL LISTADCLOBJ "B" 0 0 0 0 "CR09"))
       (SETQ LISTADCLOBJ (MBDDCL LISTADCLOBJ "B" 0 0 0 0 "CR010"))
    )
  )
  (if (= objetos "cr03")
    (progn
       (SETQ LISTADCLOBJ (MBDDCL LISTADCLOBJ "B" 0 0 0 0 "CR011"))
       (SETQ LISTADCLOBJ (MBDDCL LISTADCLOBJ "B" 0 0 0 0 "CR012"))
       (SETQ LISTADCLOBJ (MBDDCL LISTADCLOBJ "B" 0 0 0 0 "CR013"))
       (SETQ LISTADCLOBJ (MBDDCL LISTADCLOBJ "B" 0 0 0 0 "CR014"))
       (SETQ LISTADCLOBJ (MBDDCL LISTADCLOBJ "B" 0 0 0 0 "CR015"))
       ;(SETQ LISTADCLOBJ (MBDDCL LISTADCLOBJ "B" 0 0 0 0 "CR016"))
       ;(SETQ LISTADCLOBJ (MBDDCL LISTADCLOBJ "B" 0 0 0 0 "CR036"))
    )
  )
  (if (= objetos "cr04")
    (progn
       (SETQ LISTADCLOBJ (MBDDCL LISTADCLOBJ "B" 0 0 0 0 "CR017"))
       (SETQ LISTADCLOBJ (MBDDCL LISTADCLOBJ "B" 0 0 0 0 "CR018"))
       (SETQ LISTADCLOBJ (MBDDCL LISTADCLOBJ "B" 0 0 0 0 "CR019"))
    )
  )
  (if (= objetos "cr05")
    (progn
       (SETQ LISTADCLOBJ (MBDDCL LISTADCLOBJ "B" 0 0 0 0 "CR020"))
       (SETQ LISTADCLOBJ (MBDDCL LISTADCLOBJ "B" 0 0 0 0 "CR021"))
    )
  )
  (if (= objetos "cr051")
    (progn
      (SETQ LISTADCLOBJ (MBDDCL LISTADCLOBJ "B" 0 0 0 0 "CR022"))
    )
  )
  (if (= objetos "cr052")
    (progn
      (SETQ LISTADCLOBJ (MBDDCL LISTADCLOBJ "B" 0 0 0 0 "CR023"))
      (SETQ LISTADCLOBJ (MBDDCL LISTADCLOBJ "B" 0 0 0 0 "CR024"))
    )
  )
  (if (= objetos "cr06")
    (progn
      (SETQ LISTADCLOBJ (MBDDCL LISTADCLOBJ "B" 0 0 0 0 "CR025"))
      (SETQ LISTADCLOBJ (MBDDCL LISTADCLOBJ "B" 0 0 0 0 "CR026"))
      (SETQ LISTADCLOBJ (MBDDCL LISTADCLOBJ "B" 0 0 0 0 "CR027"))
      (SETQ LISTADCLOBJ (MBDDCL LISTADCLOBJ "B" 0 0 0 0 "CR028"))
      (SETQ LISTADCLOBJ (MBDDCL LISTADCLOBJ "B" 0 0 0 0 "CR029"))
      (SETQ LISTADCLOBJ (MBDDCL LISTADCLOBJ "B" 0 0 0 0 "CR030"))
      (SETQ LISTADCLOBJ (MBDDCL LISTADCLOBJ "B" 0 0 0 0 "CR031"))
      (SETQ LISTADCLOBJ (MBDDCL LISTADCLOBJ "B" 0 0 0 0 "CR032"))
      (SETQ LISTADCLOBJ (MBDDCL LISTADCLOBJ "B" 0 0 0 0 "CR033"))
    )
  )
  (if (= objetos "cr07")
    (progn
      (SETQ LISTADCLOBJ (MBDDCL LISTADCLOBJ "B" 0 0 0 0 "CR034"))
      (SETQ LISTADCLOBJ (MBDDCL LISTADCLOBJ "B" 0 0 0 0 "CR035"))
    )
  )
)

(defun activa (objetos)
  (if (= LISTADCLOBJ nil) (setq LISTADCLOBJ ""))
  (if (= objetos "opf")
    (SETQ LISTADCLOBJ (MBDDCL LISTADCLOBJ "A" 11 427 23 439 "opf"))
  )
  (if (= objetos "INDICES")
    (progn
      (SETQ LISTADCLOBJ (MBDDCL LISTADCLOBJ "A" 11 289 77 503 "INDICE1"))
      (SETQ LISTADCLOBJ (MBDDCL LISTADCLOBJ "A" 87 307 163 485 "INDICE2"))
    )
  )
  (if (= objetos "control")
    (progn
      (SETQ LISTADCLOBJ (MBDDCL LISTADCLOBJ "A" 485 482 517 522 "av1"))
      (SETQ LISTADCLOBJ (MBDDCL LISTADCLOBJ "A" 522 482 554 522 "av2"))
      (SETQ LISTADCLOBJ (MBDDCL LISTADCLOBJ "A" 559 482 591 522 "av3"))
      (SETQ LISTADCLOBJ (MBDDCL LISTADCLOBJ "A" 596 482 628 522 "av4"))
    )
  )
  (if (= objetos "gb")
    (progn
      (SETQ LISTADCLOBJ (MBDDCL LISTADCLOBJ "A" 10 531 105 596 "GEVAPORA1"))
      (SETQ LISTADCLOBJ (MBDDCL LISTADCLOBJ "A" 110 531 205 596 "GGRANIZO"))
      (SETQ LISTADCLOBJ (MBDDCL LISTADCLOBJ "A" 210 531 305 596 "GPRECIPITACION"))
      (sETQ LISTADCLOBJ (MBDDCL LISTADCLOBJ "A" 310 531 405 596 "GNIEBLA"))
      (SETQ LISTADCLOBJ (MBDDCL LISTADCLOBJ "A" 410 531 504 596 "GNUBLADOS"))
      (SETQ LISTADCLOBJ (MBDDCL LISTADCLOBJ "A" 509 531 604 596 "GTELECT"))
      (SETQ LISTADCLOBJ (MBDDCL LISTADCLOBJ "A" 609 531 704 596 "GTEMP"))
      (SETQ LISTADCLOBJ (MBDDCL LISTADCLOBJ "A" 709 531 804 596 "GTEMPMIN"))
      (SETQ LISTADCLOBJ (MBDDCL LISTADCLOBJ "A" 809 531 904 596 "GTEMPMAX"))
    )
  )
  (if (= objetos "fb")
    (progn
      (SETQ LISTADCLOBJ (MBDDCL LISTADCLOBJ "A" 6 24 18 36 "FGRANIZO"))
      (SETQ LISTADCLOBJ (MBDDCL LISTADCLOBJ "A" 6 40 18 52 "FPRECIPITACION"))
      (SETQ LISTADCLOBJ (MBDDCL LISTADCLOBJ "A" 6 56 18 68 "FNIEBLA"))
      (SETQ LISTADCLOBJ (MBDDCL LISTADCLOBJ "A" 6 72 18 84 "FNUBLADOS"))
      (SETQ LISTADCLOBJ (MBDDCL LISTADCLOBJ "A" 6 88 18 100 "FTELECTR"))
      (SETQ LISTADCLOBJ (MBDDCL LISTADCLOBJ "A" 6 104 18 116 "FTEMP"))
      (SETQ LISTADCLOBJ (MBDDCL LISTADCLOBJ "A" 6 120 18 132 "FTEMPMIN"))
      (SETQ LISTADCLOBJ (MBDDCL LISTADCLOBJ "A" 6 136 18 148 "FEVAPORA"))
      (SETQ LISTADCLOBJ (MBDDCL LISTADCLOBJ "A" 6 152 18 164 "FTEMPMAX"))
    )
  )
  (if (= objetos "pesta")
    (progn
      (SETQ LISTADCLOBJ (MBDDCL LISTADCLOBJ "A" 183 5 312 18 "TXT0"))
      (SETQ LISTADCLOBJ (MBDDCL LISTADCLOBJ "A" 321 5 412 18 "TXT1"))
    )
  )
  (if (= objetos "mapa")
    (SETQ LISTADCLOBJ (MBDDCL LISTADCLOBJ "A" 100 0 918 524 "DIBUJO"))
  )
  (if (= objetos "bp01")
    (progn
       (SETQ LISTADCLOBJ (MBDDCL LISTADCLOBJ "A" 181 25 225 41 "BT01"))
       (SETQ LISTADCLOBJ (MBDDCL LISTADCLOBJ "A" 229 25 306 41 "BT02"))
       (SETQ LISTADCLOBJ (MBDDCL LISTADCLOBJ "A" 310 25 350 41 "BT03"))
       (SETQ LISTADCLOBJ (MBDDCL LISTADCLOBJ "A" 354 25 382 41 "BT04"))
       (SETQ LISTADCLOBJ (MBDDCL LISTADCLOBJ "A" 386 25 441 41 "BT05"))
    )
  )
  (if (= objetos "bp11")
    (progn
       (SETQ LISTADCLOBJ (MBDDCL LISTADCLOBJ "A" 181 25 263 41 "BT11"))
       (SETQ LISTADCLOBJ (MBDDCL LISTADCLOBJ "A" 266 25 377 41 "BT12"))
    )
  )
  (if (= objetos "cr01")
    (progn
       (SETQ LISTADCLOBJ (MBDDCL LISTADCLOBJ "A" 6 24 18 36 "CR01"))
       (SETQ LISTADCLOBJ (MBDDCL LISTADCLOBJ "A" 6 40 18 52 "CR02"))
       (SETQ LISTADCLOBJ (MBDDCL LISTADCLOBJ "A" 6 56 18 68 "CR03"))
       (SETQ LISTADCLOBJ (MBDDCL LISTADCLOBJ "A" 6 72 18 84 "CR04"))
    )
  )
  (if (= objetos "cr02")
    (progn
       (SETQ LISTADCLOBJ (MBDDCL LISTADCLOBJ "A" 6 24 18 36 "CR05"))
       (SETQ LISTADCLOBJ (MBDDCL LISTADCLOBJ "A" 6 40 18 52 "CR06"))
       (SETQ LISTADCLOBJ (MBDDCL LISTADCLOBJ "A" 6 56 18 68 "CR07"))
       (SETQ LISTADCLOBJ (MBDDCL LISTADCLOBJ "A" 6 72 18 84 "CR08"))       
       (SETQ LISTADCLOBJ (MBDDCL LISTADCLOBJ "A" 6 88 18 100 "CR09"))
       (SETQ LISTADCLOBJ (MBDDCL LISTADCLOBJ "A" 6 104 18 116 "CR010"))
    )
  )
  (if (= objetos "cr03")
    (progn
       (SETQ LISTADCLOBJ (MBDDCL LISTADCLOBJ "A" 6 24 18 36 "CR011"))
       (SETQ LISTADCLOBJ (MBDDCL LISTADCLOBJ "A" 6 40 18 52 "CR012"))
       (SETQ LISTADCLOBJ (MBDDCL LISTADCLOBJ "A" 6 56 18 68 "CR013"))
       (SETQ LISTADCLOBJ (MBDDCL LISTADCLOBJ "A" 6 72 18 84 "CR014"))       
       (SETQ LISTADCLOBJ (MBDDCL LISTADCLOBJ "A" 6 88 18 100 "CR015"))
       ;(SETQ LISTADCLOBJ (MBDDCL LISTADCLOBJ "A" 6 104 18 116 "CR016"))
       ;(SETQ LISTADCLOBJ (MBDDCL LISTADCLOBJ "A" 6 120 18 132 "CR036"))
    )
  )
  (if (= objetos "cr04")
    (progn
      (SETQ LISTADCLOBJ (MBDDCL LISTADCLOBJ "A" 35 107 103 137 "CR019"))
      (SETQ LISTADCLOBJ (MBDDCL LISTADCLOBJ "A" 35 41 103 71 "CR017"))
      (SETQ LISTADCLOBJ (MBDDCL LISTADCLOBJ "A" 35 74 103 104 "CR018"))
    )
  )
  (if (= objetos "cr05")
    (progn
      (SETQ LISTADCLOBJ (MBDDCL LISTADCLOBJ "A" 91 27 147 52 "CR021"))
      (SETQ LISTADCLOBJ (MBDDCL LISTADCLOBJ "A" 20 27 76 52 "CR020"))
    )
  )
  (if (= objetos "cr051")
    (progn
      (SETQ LISTADCLOBJ (MBDDCL LISTADCLOBJ "A" 6 64 170 250 "CR022"))
    )
  )
  (if (= objetos "cr052")
    (progn
      (SETQ LISTADCLOBJ (MBDDCL LISTADCLOBJ "A" 11 72 169 190 "CR023"))
      (SETQ LISTADCLOBJ (MBDDCL LISTADCLOBJ "A" 11 192 83 239 "CR024"))
    )
  )
  (if (= objetos "cr06")
    (progn
      (SETQ LISTADCLOBJ (MBDDCL LISTADCLOBJ "A" 6 24 18 36 "CR025"))
      (SETQ LISTADCLOBJ (MBDDCL LISTADCLOBJ "A" 6 40 18 52 "CR026"))
      (SETQ LISTADCLOBJ (MBDDCL LISTADCLOBJ "A" 6 56 18 68 "CR027"))
      (SETQ LISTADCLOBJ (MBDDCL LISTADCLOBJ "A" 6 72 18 84 "CR028"))
      (SETQ LISTADCLOBJ (MBDDCL LISTADCLOBJ "A" 6 88 18 100 "CR029"))
      (SETQ LISTADCLOBJ (MBDDCL LISTADCLOBJ "A" 6 104 18 116 "CR030"))
      (SETQ LISTADCLOBJ (MBDDCL LISTADCLOBJ "A" 6 120 18 132 "CR031"))
      (SETQ LISTADCLOBJ (MBDDCL LISTADCLOBJ "A" 6 136 18 148 "CR032"))
      (SETQ LISTADCLOBJ (MBDDCL LISTADCLOBJ "A" 6 152 18 164 "CR033"))
    )
  )
  (if (= objetos "cr07")
    (progn
      (SETQ LISTADCLOBJ (MBDDCL LISTADCLOBJ "A" 62 64 115 117 "CR034"))
      (SETQ LISTADCLOBJ (MBDDCL LISTADCLOBJ "A" 62 161 115 214 "CR035"))
    )
  )
)
