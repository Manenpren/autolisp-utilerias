(defun c:rblock ()
        (setq e (car (entsel "Selecciona el texto a rotar : ")))
        (setq NOMBRE (cdr (assoc 2 (entget e))))
        (setq AN (getreal "Dame el angulo al que deseas rotar: "))
        (setq E (entnext))
        (while E
          (if (= "INSERT" (cdr (assoc 0 (entget E))))
              (if (= (strcase NOMBRE) (cdr (assoc 2 (entget E))))
                   (command "CHANGE" E "" "" "" AN)
              )
          )
         (setq E (entnext E))
        )
)
