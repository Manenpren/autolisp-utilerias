(defun tercerp ()
  (setq a "Para realizar el llenado de datos se requiere un \n")
  (setq b "calculo previo de la correlacion entre las estaciones\n")
  (setq c "si no va a utilizar los comandos de llenado de datos \n")
  (setq d "puede omitir este paso")
  (setq text (strcat a b c d))
  (setq buttons (list "Calcular" "Cancelar"))
 (if (= (dos_msgboxex text "Question of the Day" buttons 4) 0)
 (progn
  (setq LISTADCLOBJ "")
  (setq LISTADCLOBJ2 "")
  (C:LIBRERIA "ENTRADAS Y SALIDAS AL REGISTRO DE OBJETOS DCL2")
  (C:LIBRERIA "ENTRADAS Y SALIDAS AL REGISTRO DE OBJETOS DCL2")
  (C:LIBRERIA "activa y desactiva objetos dcl")
  (C:LIBRERIA "dibuja objetos en pantalla")
  (C:LIBRERIA "BUSCA ACCION OBJETOS DIALOGO2")
  (C:LIBRERIA "intercambio excel")
  (C:LIBRERIA "lee datos estacion excel")
  (C:LIBRERIA "escribe texto img justif")
  (C:LIBRERIA "genera reportes")
  (C:LIBRERIA "lee datos estacion")
  (C:LIBRERIA "persistencia anderson")
  (C:LIBRERIA "prueba de secuencias")
  (C:LIBRERIA "test de helmert")
  (C:LIBRERIA "test mann kendall")
  (C:LIBRERIA "test cramer")
  (C:LIBRERIA "test student")
  (C:LIBRERIA "regresion lineal")
  (C:LIBRERIA "correlacionvarios")
  (C:LIBRERIA "genera reporte CORRELACION")
  (C:LIBRERIA "funcion grafica2")
  (C:LIBRERIA "fecha to fecha cadena")
  (C:LIBRERIA "ranges")
  (C:LIBRERIA "reportes")
  (setq Xcolocaesta nil)
  (setq graf 0)
;  (SETQ ANCHOGRFVAL 0)
;  (SETQ FECHAINIGRF "")
  (activa2 "mapa2")
  (activa2 "mapa3")
  (limpiaest)
  ;(setq nestclicom (LENGTH esataciones3))
  (dialogo3)
  ;(if (= opback "s")(regresap))
  (setq nestx 1);1	
 )
 )
;(setq matrizcorrelac (correlacionv listacorr "C" DATOSFT2 "19000101" DATOSFT1 DATOSFT3))
  (LOAD (STRCAT RUTA "revisa datos climatologicos"))
  (segundoP)
)

(defun limpiaest ()
  (setq nest 1);1	
  (setq nestfc (/ (strlen ESTACFINALC) 5))
  (setq nestfe (/ (strlen ESTACFINALE) 5))
  (setq xinicialmapa 12);144
  (setq yinicialmapa 12)
  (setq anchomapa 400);642
  (setq altomapa 250);580
  (setq xinicialmapa2 6);144
  (setq yinicialmapa2 9)
  (setq anchomapa2 600);642
  (setq altomapa2 600);580
  (setq GBMIN (list (- (car CENTROIDEC) DBUS) (- (cadr CENTROIDEC) DBUS)));IMAGEN2
  (setq GBMAX (list (+ (car CENTROIDEC) DBUS) (+ (cadr CENTROIDEC) DBUS)))
  (setq GBMIN (UTM-GEO GBMIN (ATOI ZONAH)))
  (setq GBMAX (UTM-GEO GBMAX (ATOI ZONAH)))
  (SETQ XGMIN (CAR GBMIN))
  (SETQ YGMIN (CADR GBMIN))
  (SETQ XGMAX (CAR GBMAX))
  (SETQ YGMAX (CADR GBMAX))
  (SETQ CUEVER 1)
  (SETQ matrizprov NIL)
  (setq estaciones3 nil)
  (setq estaciones4 nil)
  (setq matrizporcentajc2 nil)
  (setq matrizporcentajE2 nil)
  (setq matrizllenacrn nil)
  (setq matrizllenaern nil)
  (setq matrizllenacpa nil)
  (setq matrizllenaepa nil)
  (setq matrizllenacmu nil)
  (setq matrizllenaemu nil)
  (setq ESTACFINALC2 "")
  (setq ESTACFINALE2 "")
  (repeat nestfc
    (setq estaccf (substr estacfinalc (1+ (* (1- CUEVER) 5)) 5))
    (setq verpol (cdr (assoc (atoi estaccf) matrizporcentajc)))
    (setq CONCATENADO (cons cuever verpol))
    (setq matrizporcentajc2 (append matrizporcentajc2 (list CONCATENADO)))
    (setq verpol (cdr (assoc (atoi estaccf) estaciones)))
    (setq CONCATENADO (cons cuever verpol));-1
    (setq estaciones3 (append estaciones3 (list CONCATENADO)))
    (setq CONCATENADO (cons (1- cuever) verpol))
    (setq CONCATENADO (cons (1- cuever) (list (atof (cadr verpol)) (atof (caddr verpol)))))
    (setq matrizprov (append matrizprov (list CONCATENADO)));(car (cdr (assoc 1 estaciones3)))
    (setq CONCATENADO (cons cuever (list (car (cdr (assoc CUEVER estaciones3))) "")))
    (setq matrizllENAcrn (append matrizllENAcrn (list CONCATENADO)));
    (SETQ CUEVER (1+ CUEVER))
  )
  (SETQ MATRIZPROVR MATRIZPROV)
  (setq matrizllenacpa matrizllenacrn)
  (setq matrizllenacmu matrizllenacrn)
  (setq barra1 nestfc)
  (setq num nestfc)
  (IF (/= matrizprov NIL)
    (SETQ MATRIZEST (TRFCOR MATRIZPROV anchomapa altomapa XGMIN YGMIN XGMAX YGMAX xinicialmapa yinicialmapa))
    (SETQ MATRIZEST NIL)
  )
  (SETQ CUEVER 1)
  (SETQ matrizprov NIL)
  (repeat nestfe
    (setq estacEf (substr estacfinalE (1+ (* (1- CUEVER) 5)) 5))
    (setq verpol (cdr (assoc (abs (atoi estacEf)) matrizporcentajE)))
    (setq CONCATENADO (cons cuever verpol))
    (setq matrizporcentajE2 (append matrizporcentajE2 (list CONCATENADO)))
    (setq verpol (cdr (assoc (abs(atoi estacef)) estaciones2)))
    (setq CONCATENADO (cons cuever verpol));-1
    (setq estaciones4 (append estaciones4 (list CONCATENADO)))
    (setq CONCATENADO (cons (1- cuever) verpol))
    (setq CONCATENADO (cons (1- cuever) (list (atof (cadr verpol)) (atof (caddr verpol)))))
    (setq matrizprov (append matrizprov (list CONCATENADO)))
    (setq CONCATENADO (cons cuever (list (car (cdr (assoc CUEVER estaciones4))) "")))
    (setq matrizllENAern (append matrizllENAern (list CONCATENADO)));
    (SETQ CUEVER (1+ CUEVER))
  )
  (setq matrizllenaepa matrizllenaern)
  (setq matrizllenaemu matrizllenaern)
  (setq barra2 nestfe)
  (setq num2 nestfe)
  (IF (/= MATRIZPROV NIL)
    (SETQ MATRIZEST2 (TRFCOR matrizprov anchomapa altomapa XGMIN YGMIN XGMAX YGMAX xinicialmapa yinicialmapa))
    (SETQ MATRIZEST2 NIL)
  )
  (IF (/= matrizd NIL)
    (SETQ MATRIZDIBU (TRFCOR matrizd anchomapa altomapa XGMIN YGMIN XGMAX YGMAX xinicialmapa yinicialmapa))
    (SETQ MATRIZDIBU NIL)
  )
  (setq num2 0) 
  (if (= eclicom "1")
    (progn
      (SETQ IDEST 1)
      (while idest
        (setq idest (cdr (assoc num2 MATRIZEST)))
        (setq num2 (1+ num2))
      )
    )
  )
  (setq num3 0) 
  (if (= eeric "1")
    (progn
      (SETQ IDEST 1)
      (while idest
        (setq idest (cdr (assoc num3 MATRIZEST2)))
        (setq num3 (1+ num3))
      )
    )
  )
  (if (/= num2 0) (setq num2 (1- num2)))
  (if (/= num3 0) (setq num3 (1- num3)))
  (setq ntest (+ num2 num3))
  (setq verpolxxx (nestacc3 nest))
  (SETQ ptX2 (ATOf (CAdR verpolxxx))) 
  (SETQ ptY2 (ATOf (CADdR verpolxxx)))

  (setq GBMINC (list (- PTX2 (/ (* DBUS 1.3) 110668.9215)) (- PTY2 (/ (* DBUS 1.3) 110668.9215))));IMAGEN1
  (setq GBMAXC (list (+ PTX2 (/ (* DBUS 1.3) 110668.9215)) (+ PTY2 (/ (* DBUS 1.3) 110668.9215))))
  (SETQ XGMINC (CAR GBMINC))
  (SETQ YGMINC (CADR GBMINC))
  (SETQ XGMAXC (CAR GBMAXC))
  (SETQ YGMAXC (CADR GBMAXC))
  (SETQ MATRIZESTD (TRFCOR MATRIZPROVR anchomapa2 altomapa2 XGMINC YGMINC XGMAXC YGMAXC xinicialmapa2 yinicialmapa2))
  (SETQ MATRIZEST2D (TRFCOR matrizprov anchomapa2 altomapa2 XGMINC YGMINC XGMAXC YGMAXC xinicialmapa2 yinicialmapa2));IMAGEN1
  (SETQ MATRIZDIBUD (TRFCOR matrizd anchomapa2 altomapa2 XGMINC YGMINC XGMAXC YGMAXC xinicialmapa2 yinicialmapa2))
)

(defun dibujo3 ()
  (start_image "imagen")                     
  (setq vzoom 1)
  (fill_image xinicialmapa yinicialmapa (+ anchomapa 12) altomapa 0)
  (SETQ CUEVER 0)
  (setq verpol (cdr (assoc cuever MATRIZDIBU)))
  (WHILE VERPOL
    (SETQ VERPOL2 VERPOL)
    (SETQ CUEVER (1+ CUEVER))
    (setq verpol (cdr (assoc cuever MATRIZDIBU)))
    (IF (AND VERPOL (/= CUEVER 0))
      (PROGN
        (SETQ X1 (ATOI (RTOS (CAR VERPOL2) 2 0))) 
        (SETQ Y1 (ATOI (RTOS (CADR VERPOL2) 2 0)))
        (SETQ X2 (ATOI (RTOS (CAR VERPOL) 2 0))) 
        (SETQ Y2 (ATOI (RTOS (CADR VERPOL) 2 0)))
        (vector_image X1 Y1 X2 Y2 1)
      )
    )
  )
  (if (= barra1 nil) (setq barra1 1))
  (if (= barra2 nil) (setq barra2 1))
  (if (/= MATRIZEST nil)
   (progn
    (SETQ CUEVER 0)
    (setq verpol (cdr (assoc cuever MATRIZEST)))
    (setq verpolxxx (cadr (assoc (1+ cuever) estaciones3)))	
    (SETQ CONTANIM 1)
    (dos_waitcursor t)
    (dos_getprogress "Trabajando" "Dibujando estaciones" barra1)
    (WHILE VERPOL
      (SETQ X (ATOI (RTOS (CAR VERPOL) 2 0))) 
      (SETQ Y (ATOI (RTOS (CADR VERPOL) 2 0)))
      (slide_image (- X 20) (- Y 20) 40 40 (STRCAT RUTA "SLIDES\\eazul.SLD"))
      (if (< contanim barra1)
        (anim2) 
      )
      (stexto verpolxxx "romans" 18 (- X 20) (- Y 40))
      (SETQ CUEVER (1+ CUEVER))
      (setq verpol (cdr (assoc cuever MATRIZEST)))
      (setq verpolxxx (cadr (assoc (1+ cuever) estaciones3)))	
    )
    (dos_getprogress t)
    (dos_waitcursor)
   )
  )
  (if (/= MATRIZEST2 nil)
   (progn
    (SETQ CUEVER 0)
    (setq verpol (cdr (assoc cuever MATRIZEST2)))
    (setq verpolxxx (cadr (assoc (1+ cuever) estaciones4)))
    (SETQ CONTANIM 1)	
    (dos_waitcursor t)
    (dos_getprogress "Trabajando" "Dibujando estaciones" barra2)
    (WHILE VERPOL
      (SETQ X (ATOI (RTOS (CAR VERPOL) 2 0))) 
      (SETQ Y (ATOI (RTOS (CADR VERPOL) 2 0)))
      (slide_image (- X 25) (- Y 20) 40 40 (STRCAT RUTA "SLIDES\\eamari.sld"))
      (if (< contanim barra2)
        (anim2) 
      )
      (stexto verpolxxx "romans" 18 (- X 25) (+ Y 20))
      (SETQ CUEVER (1+ CUEVER))
      (setq verpol (cdr (assoc cuever MATRIZEST2)))
      (setq verpolxxx (cadr (assoc (1+ cuever) estaciones4)))	
    )
    (dos_getprogress t)
    (dos_waitcursor)
   )
  )
  (slide_image (+ xinicialmapa 355) (+ yinicialmapa 8) 40 48 (STRCAT RUTA "SLIDES\\MAPA2(NORTE).sld"))
;  (activa2 "MPRINCIPAL")
;  (activa2 "DATOSF")
;  (activa2 "SELEC")
;  (dibujaptn)
;  (slide_image 795 456 74 9 (STRCAT RUTA "SLIDES\\seleccionar.sld"))
  (end_image)
)

(defun dibujo4 ()
  (start_image "imagen2")                     
  (setq vzoom 1)
  (fill_image xinicialmapa2 yinicialmapa2 (+ anchomapa2 12) altomapa2 0)
  (SETQ CUEVER 0)
  (setq verpol (cdr (assoc cuever MATRIZDIBUd)))
  (WHILE VERPOL
    (SETQ VERPOL2 VERPOL)
    (SETQ CUEVER (1+ CUEVER))
    (setq verpol (cdr (assoc cuever MATRIZDIBUd)))
    (IF (AND VERPOL (/= CUEVER 0))
      (PROGN
        (SETQ X1 (ATOI (RTOS (CAR VERPOL2) 2 0))) 
        (SETQ Y1 (ATOI (RTOS (CADR VERPOL2) 2 0)))
        (SETQ X2 (ATOI (RTOS (CAR VERPOL) 2 0))) 
        (SETQ Y2 (ATOI (RTOS (CADR VERPOL) 2 0)))
;        (vector_image X1 Y1 X2 Y2 1)
      )
    )
  )
  (if (= barra1 nil) (setq barra1 1))
  (if (= barra2 nil) (setq barra2 1))
  (if (/= MATRIZESTD nil)
   (progn
    (SETQ CUEVER 0)
    (setq verpol (cdr (assoc cuever MATRIZESTD)))
    (setq verpolxxx (cadr (assoc (1+ cuever) estaciones3)))	
    (SETQ CONTANIM 1)
    (dos_waitcursor t)
    (dos_getprogress "Trabajando" "Dibujando estaciones" barra1)
    (WHILE VERPOL
      (SETQ X (ATOI (RTOS (CAR VERPOL) 2 0))) 
      (SETQ Y (ATOI (RTOS (CADR VERPOL) 2 0)))
      (slide_image (- X 20) (- Y 20) 40 40 (STRCAT RUTA "SLIDES\\eazul.SLD"))
      (if (< contanim barra1)
        (anim2) 
      )
      (stexto verpolxxx "romans" 18 (- X 20) (- Y 40))
      (SETQ CUEVER (1+ CUEVER))
      (setq verpol (cdr (assoc cuever MATRIZESTD)))
      (setq verpolxxx (cadr (assoc (1+ cuever) estaciones3)))	
    )
    (dos_getprogress t)
    (dos_waitcursor)
   )
  )
  (if (/= MATRIZEST2D nil)
   (progn
    (SETQ CUEVER 0)
    (setq verpol (cdr (assoc cuever MATRIZEST2D)))
    (setq verpolxxx (cadr (assoc (1+ cuever) estaciones4)))
    (SETQ CONTANIM 1)	
    (dos_waitcursor t)
    (dos_getprogress "Trabajando" "Dibujando estaciones" barra2)
    (WHILE VERPOL
      (SETQ X (ATOI (RTOS (CAR VERPOL) 2 0))) 
      (SETQ Y (ATOI (RTOS (CADR VERPOL) 2 0)))
      (slide_image (- X 25) (- Y 20) 40 40 (STRCAT RUTA "SLIDES\\eamari.sld"))
      (if (< contanim barra2)
        (anim2) 
      )
      (stexto verpolxxx "romans" 18 (- X 25) (+ Y 20))
      (SETQ CUEVER (1+ CUEVER))
      (setq verpol (cdr (assoc cuever MATRIZEST2D)))
      (setq verpolxxx (cadr (assoc (1+ cuever) estaciones4)))	
    )
    (dos_getprogress t)
    (dos_waitcursor)
   )
  )
  (slide_image (+ xinicialmapa 560) (+ yinicialmapa 8) 40 48 (STRCAT RUTA "SLIDES\\MAPA2(NORTE).sld"))
  (end_image)
)

(defun dialogo3()
;  (SETQ VARGRF2 "001190001011900010120000101200001011010001001")
  (setq estaciones2 estaciones4)
  (setq estaciones estaciones3)
  (setq dcl_id (load_dialog (strcat ruta "dialogos\\estaciones climatologicas.dcl"))) 
  (new_dialog "EST3" dcl_id)
  (DIBUJO3)
  (DIBUJO4)
  (action_tile "utlr" "(v1)")
  (action_tile "utlp" "(v2)")
  (action_tile "utlus" "(v3)")
  (action_tile "estar" "(v92)")
  (action_tile "estab" "(V102)")
  (action_tile "cancel" "(exit)")
  (action_tile "imagen2" "(picaste4 $x $y)")
  (action_tile "imagen" "(picaste3 $x $y)")
  (action_tile "regreasaatras" "(cerrar)")
;  (setq width (dimx_tile  "imagen")
;        height (dimy_tile "imagen"))
;  (setq width2 (dimx_tile  "imagen2")
;        height2 (dimy_tile "imagen2"))
  (start_dialog)                          ; Display the dialog                                      ; box.
  (unload_dialog dcl_id)                  ; Unload the DCL file.
  (princ)
)

(defun cerrar ()
  (setq opback "s")
  (done_dialog dcl_id)
;  (regresap)
)

(defun regresap()
;  (exit)
  (unload_dialog dcl_id)
  (C:LIBRERIA "UTM-GEO")
  (C:LIBRERIA "GEO-UTM")
  (C:LIBRERIA "encuentra zona horaria municipio")
  (C:LIBRERIA "CENTROIDE DE UN POLIGONO IRREGULAR2")
  (C:LIBRERIA "VERTICES TO BD POLYLINE")
  (C:LIBRERIA "BUSCA ESTACIONES CLIMATOLOGICAS CLICOM")
  (C:LIBRERIA "BUSCA ESTACIONES CLIMATOLOGICAS ERICK")
  (C:LIBRERIA "BUSCA ESTADO DE GEO")
  (C:LIBRERIA "tranforma coordenadas dibujo im")
  (C:LIBRERIA "escribe texto img")
  (C:LIBRERIA "acota grafica")
  (C:LIBRERIA "ENTRADAS Y SALIDAS AL REGISTRO DE OBJETOS DCL")
  (C:LIBRERIA "BUSCA ACCION OBJETOS DIALOGO")
  (C:LIBRERIA "descompacta cadena")
  (C:LIBRERIA "grafica parametro clima estacion")
  (C:LIBRERIA "controla grafica")
  (C:LIBRERIA "sector cuadricula")
  (C:LIBRERIA "muestra color")
  (C:LIBRERIA "numero de dias del mes fecha")
  (C:LIBRERIA "indice graficos fechas")
  (setq numeroindicef "01")
  (setq numeroindicet "001")
  (setq estaciones nil)
  (setq estaciones2 nil)
  (setq listadclobj "")
  (COMMAND "UNDO" "M")
  (setq contz 0)
  (setq procedencia "")
  (setq ESTACFINALC "")
  (setq ESTACFINALE "")
  (SETQ DIALOGOGRF "0116511052000000000")
  (setq colorgrf "007131141140142152154164166176178")
  (SETQ DATCLIMASOBRE "1")
  (LOAD (STRCAT RUTAFAS "ENCUENTRA ESTACIONES CLIMATICAS"))
  (setq xyz (list (car CENTROIDEC) (cadr CENTROIDEC)))
  (setq puntogeo (UTM-GEO xyz (ATOI ZONAH)))
  (SETQ CUEVER 0)
  (setq verpol (cdr (assoc cuever BDPOLI)))
  (SETQ XMIN (RTOS (car VERPOL) 2 5))
  (SETQ YMIN (RTOS (caDr VERPOL) 2 5))
  (SETQ XMAX (RTOS (car VERPOL) 2 5))
  (SETQ YMAX (RTOS (caDr VERPOL) 2 5))
  (SETQ matrizd NIL)
  (WHILE VERPOL
    (setq puntogeox (UTM-GEO (list (car verpol) (cadr verpol)) (ATOI ZONAH)))
    (setq CONCATENADOx (cons cuever puntogeox))
    (setq matrizd (append matrizd (list CONCATENADOx)))
    (SETQ XI (RTOS (car VERPOL) 2 5))
    (SETQ YI (RTOS (caDr VERPOL) 2 5))
    (IF (> XI XMAX)(SETQ XMAX XI))
    (IF (< XI XMIN)(SETQ XMIN XI))
    (IF (> YI YMAX)(SETQ YMAX YI))
    (IF (< YI YMIN)(SETQ YMIN YI))
    (SETQ CUEVER (1+ CUEVER))
    (setq verpol (cdr (assoc cuever BDPOLI)))
  )
  (if (> (abs (- (atof xmin) (atof xmax))) (abs (- (atof ymin) (atof ymax))))
    (setq dbus (fix (* 0.6 (abs (- (atof xmin) (atof xmax))))))
    (setq dbus (fix (* 0.6 (abs (- (atof ymin) (atof ymax))))))
  )
  (setq GBMIN (list (- (car CENTROIDEC) DBUS) (- (cadr CENTROIDEC) DBUS)))
  (setq GBMAX (list (+ (car CENTROIDEC) DBUS) (+ (cadr CENTROIDEC) DBUS)))
  (setq GBMIN (UTM-GEO GBMIN (ATOI ZONAH)))
  (setq GBMAX (UTM-GEO GBMAX (ATOI ZONAH)))
  (busca gbmin gbmax)
  (while (and (= estaciones nil) (= estaciones2 nil))
    (dos_splash (strcat ruta "ajuste.htj") 2)
    (setq dbus (* 1.4 dbus))
    (setq GBMIN (list (- (car CENTROIDEC) DBUS) (- (cadr CENTROIDEC) DBUS)))
    (setq GBMAX (list (+ (car CENTROIDEC) DBUS) (+ (cadr CENTROIDEC) DBUS)))
    (setq GBMIN (UTM-GEO GBMIN (ATOI ZONAH)))
    (setq GBMAX (UTM-GEO GBMAX (ATOI ZONAH)))
    (busca gbmin gbmax)
  )
   (SETQ LISTADCLOBJ (MBDDCL LISTADCLOBJ "B" 0 0 0 0 "DIBUJO"))
  (dialogox)
    (if (= opbusqueda "s") (segundop))
  (while (= opbusqueda "b")
    (setq GBMIN (list (- (car CENTROIDEC) DBUS) (- (cadr CENTROIDEC) DBUS)))
    (setq GBMAX (list (+ (car CENTROIDEC) DBUS) (+ (cadr CENTROIDEC) DBUS)))
    (setq GBMIN (UTM-GEO GBMIN (ATOI ZONAH)))
    (setq GBMAX (UTM-GEO GBMAX (ATOI ZONAH)))
    (busca gbmin gbmax)
    (while (and (= estaciones nil) (= estaciones2 nil))
      (dos_splash (strcat ruta "ajuste.htj") 2)
      (setq dbus (* 1.4 dbus))
      (setq GBMIN (list (- (car CENTROIDEC) DBUS) (- (cadr CENTROIDEC) DBUS)))
      (setq GBMAX (list (+ (car CENTROIDEC) DBUS) (+ (cadr CENTROIDEC) DBUS)))
      (setq GBMIN (UTM-GEO GBMIN (ATOI ZONAH)))
      (setq GBMAX (UTM-GEO GBMAX (ATOI ZONAH)))
      (busca gbmin gbmax)
    );while
    (dialogox)
  )
  (load (strcat RUTAFAS "revisa datos climatologicos"))
  (segundop)
;;  (regresapp)
 )
 
(defun picaste3 (x y)
;  (if (= MOUSE "DIBUJO2")
;     (DIBUJO3)
;  )
  (setq xesta x)
  (setq yesta y)
  (if (or (= mouser nil) (/= mouser mouse)) (setq mouser mouse))
  (if (or (= mouse2r nil) (/= mouse2r mouse2)) (setq mouse2r mouse2))
  (SETQ MOUSE (BUSACC2 LISTADCLOBJ X Y 74))
  (SETQ MOUSE2 (BUSACC2 LISTADCLOBJ2 X Y 274))
  (if (= MOUSE "DIBUJO2")
    (progn
      (SETQ OBJETO (BUSOBJBD LISTADCLOBJ 74 MOUSE));74??
      (setq statusobj (SUBSTR OBJETO 32 1))
      (IF (= statusobj "0")
       (PROGN
       (setq kx x)
       (setq ky y)
       (DESTA2 vzoom)
       (setq x kx)
       (setq y ky)
       (setq dstx 1000000)
       (setq num22x 0)
       (if (/= MATRIZEST nil)
         (progn
           (SETQ IDESTx 1)
           (setq idestx (cdr (assoc num22x MATRIZEST)))
           (while idestx
             (SETQ pX (ATOI (RTOS (CAR idestx) 2 0)))
             (SETQ pY (ATOI (RTOS (CADR idestx) 2 0)))
             (setq distxc (distance (list x y) (list px py)))
             (if (< distxc dstx) 
 	      (progn
                 (setq dstx distxc)
                 (setq nestc (1+ num22x))
               )      
             )
             (setq num22x (1+ num22x))
             (setq idestx (cdr (assoc num22x MATRIZEST)))
           )
         )
       )
       (setq distxc dstx)
       (setq num3x 0) 
       (if (/= MATRIZEST2 nil)
         (progn
           (SETQ IDESTx 1)
           (setq idestx (cdr (assoc num3x MATRIZEST2)))
           (while idestx
             (SETQ pX (ATOI (RTOS (CAR idestx) 2 0)))
             (SETQ pY (ATOI (RTOS (CADR idestx) 2 0)))
             (setq distxe (distance (list x y) (list (- px 5) py)))
             (if (< distxe dstx) 
	      (progn 
                (setq dstx distxe)
                (setq neste (1+ num3x ));num2+
              )      
            )  
            (setq num3x (1+ num3x))
            (setq idestx (cdr (assoc num3x MATRIZEST2)))
          )    
        )
      )
       (setq distxe dstx)
       (if (< distxe distxc) (setq nest (+ neste nestfc))(setq nest nestc))
       (dpuntero2 vzoom)
       (dibujag2)
       (dibujo4)
      )
      )
    )
  )
)

(defun dibujag2 ()
  (setq verpolxxx (nestacc3 nest))
  (SETQ ptX2 (ATOf (CAdR verpolxxx))) 
  (SETQ ptY2 (ATOf (CADdR verpolxxx)))
  (setq GBMINC (list (- PTX2 (/ (* DBUS 1.3) 110668.9215)) (- PTY2 (/ (* DBUS 1.3) 110668.9215))));IMAGEN1
  (setq GBMAXC (list (+ PTX2 (/ (* DBUS 1.3) 110668.9215)) (+ PTY2 (/ (* DBUS 1.3) 110668.9215))))
  (SETQ XGMINC (CAR GBMINC))
  (SETQ YGMINC (CADR GBMINC))
  (SETQ XGMAXC (CAR GBMAXC))
  (SETQ YGMAXC (CADR GBMAXC))
  (SETQ MATRIZESTD (TRFCOR MATRIZPROVR anchomapa2 altomapa2 XGMINC YGMINC XGMAXC YGMAXC xinicialmapa2 yinicialmapa2))
  (SETQ MATRIZEST2D (TRFCOR matrizprov anchomapa2 altomapa2 XGMINC YGMINC XGMAXC YGMAXC xinicialmapa2 yinicialmapa2));IMAGEN1
  (SETQ MATRIZDIBUD (TRFCOR matrizd anchomapa2 altomapa2 XGMINC YGMINC XGMAXC YGMAXC xinicialmapa2 yinicialmapa2))
)
 
(defun picaste4 (x y)
  (setq xesta x)
  (setq yesta y)
;  (if (or (= mouser nil) (/= mouser mouse)) (setq mouser mouse))
;  (if (or (= mouse2r nil) (/= mouse2r mouse2)) (setq mouse2r mouse2))
;  (SETQ MOUSE (BUSACC2 LISTADCLOBJ X Y 74))
;  (SETQ MOUSE2 (BUSACC2 LISTADCLOBJ2 X Y 274))
;  (if (= MOUSE "DIBUJO3")
;    (progn
      (SETQ OBJETO (BUSOBJBD LISTADCLOBJ 74 MOUSE));74??
      (setq statusobj (SUBSTR OBJETO 32 1))
      (IF (= statusobj "0")
       (PROGN
       (setq kx x)
       (setq ky y)
       (DESTA3 vzoom)
       (setq x kx)
       (setq y ky)
       (setq dstx 1000000)
       (setq num22x 0)
       (if (/= MATRIZESTD nil)
         (progn
           (SETQ IDESTx 1)
           (setq idestx (cdr (assoc num22x MATRIZESTD)))
           (while idestx
             (SETQ pX (ATOI (RTOS (CAR idestx) 2 0)))
             (SETQ pY (ATOI (RTOS (CADR idestx) 2 0)))
             (setq distxc (distance (list x y) (list px py)))
             (if (< distxc dstx) 
 	      (progn
                 (setq dstx distxc)
                 (setq nestc (1+ num22x))
               )      
             )
             (setq num22x (1+ num22x))
             (setq idestx (cdr (assoc num22x MATRIZESTD)))
           )
         )
       )
       (setq distxc dstx)
       (setq num3x 0) 
       (if (/= MATRIZEST2D nil)
         (progn
           (SETQ IDESTx 1)
           (setq idestx (cdr (assoc num3x MATRIZEST2D)))
           (while idestx
             (SETQ pX (ATOI (RTOS (CAR idestx) 2 0)))
             (SETQ pY (ATOI (RTOS (CADR idestx) 2 0)))
             (setq distxe (distance (list x y) (list (- px 5) py)))
             (if (< distxe dstx) 
	      (progn 
                (setq dstx distxe)
                (setq neste (1+ num3x ));num2+
              )      
            )  
            (setq num3x (1+ num3x))
            (setq idestx (cdr (assoc num3x MATRIZEST2D)))
          )    
        )
      )
        (setq distxe dstx)
       (if (< distxe distxc) (setq nestx (+ neste nestfc))(setq nestx nestc))
       (dpuntero3 vzoom)
       (revisasel)

      )
      )

;    )
;  )
)

(defun cuentaer2 (fechaini fechafin tipodat);(cuentaer2 fechaini fechafin tipoprof)
  (if (= tipodat "AN")
    (setq nelementos (- (atoi (substr fechafin 1 4)) (atoi (substr fechaini 1 4))))
  )
  (if (= tipodat "ME")
    (progn
      (setq fret (substr fechaini 1 6))
      (setq nelementos 1)
      (while (/= fret (substr fechafin 1 6))
        (setq fret (mesmas fret))
        (setq nelementos (1+ nelementos))
      )
    )
  )
  (if (= tipodat "ST")
    (progn
      (setq fret (substr fechaini 1 6))
      (setq nelementos 1)
      (while (/= fret (substr fechafin 1 6))
        (setq mes (substr fret 5 2))
        (if (= mes "01") (setq ndias 31))
        (if (= mes "03") (setq ndias 31))
        (if (= mes "04") (setq ndias 30))
        (if (= mes "05") (setq ndias 31))
        (if (= mes "06") (setq ndias 30))
        (if (= mes "07") (setq ndias 31))
        (if (= mes "08") (setq ndias 31))
        (if (= mes "09") (setq ndias 30))
        (if (= mes "10") (setq ndias 31))
        (if (= mes "11") (setq ndias 30))
        (if (= mes "12") (setq ndias 31))
        (if (= mes "02")
          (progn
            (setq fx (atoi (substr fret 1 4)))
            (setq dx (* (fix (/ fx 4)) 4))
            (if (= dx fx)
               (setq ndias 29)
               (setq ndias 28)
            )
          )
        );if
        (setq fret (mesmas fret))
        (if (= nelementos 0)
          (setq nelementos (+ nelementos (- ndias (1- (atoi (substr fechaini 7 2))))))
          (setq nelementos (+ nelementos ndias))
        )
      )
      (setq mes (substr fret 5 2))
      (if (= mes "01") (setq ndias 31))
      (if (= mes "03") (setq ndias 31))
      (if (= mes "04") (setq ndias 30))
      (if (= mes "05") (setq ndias 31))
      (if (= mes "06") (setq ndias 30))
      (if (= mes "07") (setq ndias 31))
      (if (= mes "08") (setq ndias 31))
      (if (= mes "09") (setq ndias 30))
      (if (= mes "10") (setq ndias 31))
      (if (= mes "11") (setq ndias 30))
      (if (= mes "12") (setq ndias 31))
      (if (= mes "02")
        (progn
          (setq fx (atoi (substr fret 1 4)))
          (setq dx (* (fix (/ fx 4)) 4))
          (if (= dx fx)
             (setq ndias 29)
             (setq ndias 28)
          )
        )
      );if
      (setq nelementos (+ nelementos ndias))
      (setq nelementos (- nelementos (- ndias (1- (atoi (substr fechafin 7 2))))))
    );progn
  )
  (if (= tipodat "MM")
    (setq nelementos 12)
  )
  (setq nelementos nelementos)
)

(defun nestacc3 (nest)
  (setq resultado nil)
  (if (and (> nest ntest) (= eclicom "1") (= eeric "1"))
    (setq resultado "no")
  )
  (if (and (<= nest ntest) (= eclicom "1") (= eeric "1"))
    (progn
      (if (<= nest num2)
        (progn
          (setq resultado (cdr (assoc nest estaciones3)));nest-1
          (setq procedencia "CLICOM")
        )
        (progn
          (setq resultado (cdr (assoc (- nest nestfc)  estaciones4)));num2-1
          (setq procedencia "ERIC")
        )
      )
    )
  )
  (if (and (> nest ntest) (= eeric "1") (/= eclicom "1"))
    (setq resultado "no")
  )
  (if (and (<= nest ntest) (= eeric "1") (/= eclicom "1"))
    (progn
      (setq resultado (cdr (assoc nest estaciones4)))
      (setq procedencia "ERIC")
    )
  )
  (if (and (> nest ntest) (/= eeric "1") (= eclicom "1"))
    (setq resultado "no")
  )
  (if (and (<= nest ntest) (/= eeric "1") (= eclicom "1"))
    (progn
      (setq resultado (cdr (assoc nest estaciones3)))
      (setq procedencia "CLICOM")
    )
  )
  (SETQ RESULTADO resultado)
)

(defun desta2 (vzoom)
  (setq xestacion (nestacc3 nest))
  (IF (or (= xestacion "no") (= xestacion nil)) (setq nest 1))
  (setq xestacion (nestacc3 nest))
  (SETQ X (ATOI (RTOS (* (atoi (CADR xestacion)) vzoom) 2 0))) 
  (SETQ Y (ATOI (RTOS (* (atoi (CADDR xestacion)) vzoom) 2 0)))
  (setq xestac2 (nestacc3 nest))
  (setq verpolxxx (car xestac2))
  (slide_image (- X 20) (- Y 20) 40 40 (STRCAT RUTA "SLIDES\\punteron.sld"))
  (if (<  nest num2)
    (slide_image (- X 20) (- Y 20) 40 40 (STRCAT RUTA "SLIDES\\punteron.sld"))
    (slide_image (- X 25) (- Y 20) 40 40 (STRCAT RUTA "SLIDES\\punteron.sld"))
  )
  (if (= procedencia "CLICOM")
   (progn
     (slide_image (- X 20) (- Y 20) 40 40 (STRCAT RUTA "SLIDES\\eazul.SLD")) 
     (stexto verpolxxx "romans" 18 (- X 20) (- Y 40))
   )
  )
  (if (= procedencia "ERIC")
   (progn
     (slide_image (- X 25) (- Y 20) 40 40 (STRCAT RUTA "SLIDES\\eamari.sld"))
     (stexto verpolxxx "romans" 18 (- X 25) (+ Y 20))
   )
  )
)

(defun desta3 (vzoom)
  (setq xestacion (nestacc3 nestx))
  (IF (or (= xestacion "no") (= xestacion nil)) (setq nestx 1))
  (setq xestacion (nestacc3 nestx))
  (SETQ X (ATOI (RTOS (* (atoi (CADR xestacion)) vzoom) 2 0))) 
  (SETQ Y (ATOI (RTOS (* (atoi (CADDR xestacion)) vzoom) 2 0)))
  (setq xestac2 (nestacc3 nestx))
  (setq verpolxxx (car xestac2))
  (slide_image (- X 20) (- Y 20) 40 40 (STRCAT RUTA "SLIDES\\punteron.sld"))
  (if (<  nest num2)
    (slide_image (- X 20) (- Y 20) 40 40 (STRCAT RUTA "SLIDES\\punteron.sld"))
    (slide_image (- X 25) (- Y 20) 40 40 (STRCAT RUTA "SLIDES\\punteron.sld"))
  )
  (if (= procedencia "CLICOM")
   (progn
     (slide_image (- X 20) (- Y 20) 40 40 (STRCAT RUTA "SLIDES\\eazul.SLD")) 
     (stexto verpolxxx "romans" 18 (- X 20) (- Y 40))
   )
  )
  (if (= procedencia "ERIC")
   (progn
     (slide_image (- X 25) (- Y 20) 40 40 (STRCAT RUTA "SLIDES\\eamari.sld"))
     (stexto verpolxxx "romans" 18 (- X 25) (+ Y 20))
   )
  )
)

(defun dpuntero2 (vzoom)
  (start_image "imagen")
  (if (/= Xcolocaesta nil)
    (progn
      (fill_image (- Xcolocaesta 25) (- Ycolocaesta 20) 41 41 0)(if(= procedencia "CLICOM")
      (slide_image (- Xcolocaesta 20) (- Ycolocaesta 20) 40 40 (STRCAT RUTA "SLIDES\\eazul.SLD")
    )
    (slide_image (- Xcolocaesta 25) (- Ycolocaesta 20) 40 40 (STRCAT RUTA "SLIDES\\eamari.sld"))))
  )
  (SETQ NDATOCLIM 3)
  (end_image)

  (leyenbtn3 nest)

  (start_image "imagen")
  (setq xestac (nestacc nest))
  (IF (or (= XESTAC "no") (= XESTAC nil)) (setq nest 1))
  (setq xestac (nestacc nest))
  (SETQ Xcolocaesta (ATOI (RTOS (* (CaR XESTAC) vzoom) 2 0))) 
  (SETQ Ycolocaesta (ATOI (RTOS (* (CAdR XESTAC) vzoom) 2 0)))
  (if (<  nest num2)
    (slide_image (- Xcolocaesta 20) (- Ycolocaesta 20) 40 40 (STRCAT RUTA "SLIDES\\puntero.sld"))
    (slide_image (- Xcolocaesta 25) (- Ycolocaesta 20) 40 40 (STRCAT RUTA "SLIDES\\puntero.sld"))
  )
  (end_image)
  (SETQ ptX (CAR puntogeo))                       ; distancia
  (SETQ ptY (CADR puntogeo))
  (setq verpolxxx (nestacc3 nest))
  (SETQ ptX2 (ATOf (CAdR verpolxxx))) 
  (SETQ ptY2 (ATOf (CADdR verpolxxx)))
  (setq distanciacnt (* 110668.9215 (distance (list ptx pty) (list ptx2 pty2))))
  (setq distanciacnt (smiles distanciacnt))

  (set_tile "DISTC" distanciacnt)
  (set_tile "CLEST" (car verpolxxx))
)

(defun dpuntero3 (vzoom)
  (start_image "imagen2")
  (if (/= Xcolocaesta nil)
    (progn
      (fill_image (- Xcolocaesta 25) (- Ycolocaesta 20) 41 41 0)(if(= procedencia "CLICOM")
      (slide_image (- Xcolocaesta 20) (- Ycolocaesta 20) 40 40 (STRCAT RUTA "SLIDES\\eazul.SLD")
    )
    (slide_image (- Xcolocaesta 25) (- Ycolocaesta 20) 40 40 (STRCAT RUTA "SLIDES\\eamari.sld"))))
  )
  (SETQ NDATOCLIM 3)
  (end_image)

  (leyenbtn4 nestx)

  (start_image "imagen2")
  (setq xestac (nestaccX nestx))
  (IF (or (= XESTAC "no") (= XESTAC nil)) (setq nestx 1))
  (setq xestac (nestaccX nestx))
  (SETQ Xcolocaesta (ATOI (RTOS (* (CaR XESTAC) vzoom) 2 0))) 
  (SETQ Ycolocaesta (ATOI (RTOS (* (CAdR XESTAC) vzoom) 2 0)))
  (if (<  nestx num2)
    (slide_image (- Xcolocaesta 20) (- Ycolocaesta 20) 40 40 (STRCAT RUTA "SLIDES\\puntero.sld"))
    (slide_image (- Xcolocaesta 25) (- Ycolocaesta 20) 40 40 (STRCAT RUTA "SLIDES\\puntero.sld"))
  )
  (end_image)

  (SETQ ptX (CAR puntogeo))                       ; distancia
  (SETQ ptY (CADR puntogeo))
  (setq verpolxxx (nestacc3 nestx))
  (SETQ ptX2 (ATOf (CAdR verpolxxx))) 
  (SETQ ptY2 (ATOf (CADdR verpolxxx)))
  (setq distanciacnt (* 110668.9215 (distance (list ptx pty) (list ptx2 pty2))))
  (setq distanciacnt (smiles distanciacnt));
  (set_tile "DISTCF" distanciacnt)
  (set_tile "CLESTF" (car verpolxxx))

  (setq verpolxxx (nestacc3 nest))
  (SETQ ptX (ATOf (CAdR verpolxxx))) 
  (SETQ ptY (ATOf (CADdR verpolxxx)))
  (setq verpolxxx (nestacc3 nestx))
  (SETQ ptX2 (ATOf (CAdR verpolxxx))) 
  (SETQ ptY2 (ATOf (CADdR verpolxxx)))
  (setq distanciacnt (* 110668.9215 (distance (list ptx pty) (list ptx2 pty2))))
  (setq distanciacnt (smiles distanciacnt));
  (set_tile "DISTBF" distanciacnt)
)

(defun leyenbtn3 (nestac)
  (if (> nestac NUM2)
    (setq ldat (cdr (assoc (- nestac NUM2) matrizporcentaje2)))
    (setq ldat (cdr (assoc nestac matrizporcentajc2)))
  )
  (setq fuentescr "romans")
  (IF (/= NDATOCLIM NIL)
    (PROGN
      (setq datocl (cdr (assoc NDATOCLIM ldat)))
      (if (= datocl "XXXXXX") (SETQ DATOCL "XXXXXXXXXXXXXXXXXXXXX"))
      (setq x1ly (+ 10 (* (1- NDATOCLIM) 100)))
      (setq x2ly (+ 70 (* (1- NDATOCLIM) 100)))
;      (fill_image 740 570 20 11 0)
;      (setq verpolly (itoa (atoi (substr datocl 18 4))))
;      (stexto verpolly fuentescr 12 (+ 740 (* 5 (- 3 (STRLEN verpolly)))) 570)
      (setq verpolly (strcat (substr datocl 13 5) "%"))
      (set_tile "PDAT" verpolly)
;      (fill_image 721 582 40 11 0)
;      (stexto verpolly fuentescr 12 (+ 721 (* 5 (- 6 (STRLEN verpolly)))) 582)
      (setq verpolly (strcat (substr datocl 1 4) "-" (substr datocl 7 4)))
      (set_tile "RDAT" verpolly)
;      (fill_image 696 594 62 11 0)
;      (stexto verpolly fuentescr 12 (+ 696 (* 5 (- 9 (STRLEN verpolly)))) 594)
      (if (= NDATOCLIM 1) (progn (setq verpolly "Evaporaracion")))
      (if (= NDATOCLIM 2) (progn (setq verpolly "Granizo")))
      (if (= NDATOCLIM 3) (progn (setq verpolly "Precipitacion")))
      (if (= NDATOCLIM 4) (progn (setq verpolly "Neblina")))
      (if (= NDATOCLIM 5) (progn (setq verpolly "Covertura del cielo")))
      (if (= NDATOCLIM 6) (progn (setq verpolly "Torm. Electricas")))
      (if (= NDATOCLIM 7) (progn (setq verpolly "Temperatura")))
      (if (= NDATOCLIM 8) (progn (setq verpolly "Temp. maxima")))
      (if (= NDATOCLIM 9) (progn (setq verpolly "Temp. minima")))
;      (fill_image 654 605 106 12 0)
;      (stexto verpolly fuentescr 12 (+ 654 (* 5 (- 19 (STRLEN verpolly)))) 605)
    )
  )
)

(defun leyenbtn4 (nestac)
  (if (> nestac NUM2)
    (setq ldat (cdr (assoc (- nestac NUM2) matrizporcentaje2)))
    (setq ldat (cdr (assoc nestac matrizporcentajc2)))
  )
  (setq fuentescr "romans")
  (IF (/= NDATOCLIM NIL)
    (PROGN
      (setq datocl (cdr (assoc NDATOCLIM ldat)))
      (if (= datocl "XXXXXX") (SETQ DATOCL "XXXXXXXXXXXXXXXXXXXXX"))
      (setq x1ly (+ 10 (* (1- NDATOCLIM) 100)))
      (setq x2ly (+ 70 (* (1- NDATOCLIM) 100)))
;      (fill_image 740 570 20 11 0)
;      (setq verpolly (itoa (atoi (substr datocl 18 4))))
;      (stexto verpolly fuentescr 12 (+ 740 (* 5 (- 3 (STRLEN verpolly)))) 570)
      (setq verpolly (strcat (substr datocl 13 5) "%"))
      (set_tile "PDATF" verpolly)
;      (fill_image 721 582 40 11 0)
;      (stexto verpolly fuentescr 12 (+ 721 (* 5 (- 6 (STRLEN verpolly)))) 582)
      (setq verpolly (strcat (substr datocl 1 4) "-" (substr datocl 7 4)))
      (set_tile "RDATF" verpolly)
;      (fill_image 696 594 62 11 0)
;      (stexto verpolly fuentescr 12 (+ 696 (* 5 (- 9 (STRLEN verpolly)))) 594)
      (if (= NDATOCLIM 1) (progn (setq verpolly "Evaporaracion")))
      (if (= NDATOCLIM 2) (progn (setq verpolly "Granizo")))
      (if (= NDATOCLIM 3) (progn (setq verpolly "Precipitacion")))
      (if (= NDATOCLIM 4) (progn (setq verpolly "Neblina")))
      (if (= NDATOCLIM 5) (progn (setq verpolly "Covertura del cielo")))
      (if (= NDATOCLIM 6) (progn (setq verpolly "Torm. Electricas")))
      (if (= NDATOCLIM 7) (progn (setq verpolly "Temperatura")))
      (if (= NDATOCLIM 8) (progn (setq verpolly "Temp. maxima")))
      (if (= NDATOCLIM 9) (progn (setq verpolly "Temp. minima")))
;      (fill_image 654 605 106 12 0)
;      (stexto verpolly fuentescr 12 (+ 654 (* 5 (- 19 (STRLEN verpolly)))) 605)
    )
  )
)

(DEFUN NPULSADO (CADENAF)
  (SETQ SAL "")
  (SETQ CONTSALDLG 1)
  (SETQ RESULTADO NIL)
  (WHILE (AND (= SAL "") (<= CONTSALDLG 20))
    (IF (= (SUBSTR cadenaF CONTSALDLG 1) "1") 
      (PROGN
        (SETQ RESULTADO CONTSALDLG)
        (SETQ SAL "S")
      )
    )
    (SETQ CONTSALDLG (1+ CONTSALDLG))
  )
  (SETQ RESULTADO RESULTADO)
)

(DEFUN DESPULSA (BOTON)
  (SETQ CONTDESP 1)
  (REPEAT 4
    (IF (/= CONTDESP (ATOI (SUBSTR BOTON 3 1)))
      (PROGN
        (SETQ EVENTOX (STRCAT "PR" (ITOA CONTDESP)))
        (SETQ OBJETO (BUSOBJBD LISTADCLOBJ 74 EVENTOX))
        (setq statusobj (SUBSTR OBJETO 32 1))
        (IF (= statusobj "1") 
          (PROGN
            (IF (= EVENTOX "PR1") 
              (PROGN
                (DESactiva2 "CONSISTENCIA")
                (fill_image 0 0 144 257 0)
              )
            )
            (IF (= EVENTOX "PR4") 
              (PROGN
                (DESactiva2 "RESUMEN")
                 (fill_image 0 0 144 235 0)
              )
            )
            (IF (= EVENTOX "PR2") 
              (PROGN
                (DESactiva2 "LLENA")
                 (fill_image 0 0 144 265 0)
              )
            )
            (IF (= EVENTOX "PR3") 
              (PROGN
                (fill_image 0 0 773 624 0)
                (activa3 "PR1")
                (activa3 "PR2")
                (activa3 "PR3")
                (activa3 "PR4")
                (activa2 "mapa")
                (activa3 "SEL1")
                (desactiva2 "TOOLSGRF")
                (dibujaelem (BUSOBJBD LISTADCLOBJ 74 "PR1"))
                (dibujaelem (BUSOBJBD LISTADCLOBJ 74 "PR2"))
                (dibujaelem (BUSOBJBD LISTADCLOBJ 74 "PR3"))
                (dibujaelem (BUSOBJBD LISTADCLOBJ 74 "PR4"))
              )
            )
            (setq LINEAFIN (strcat (substr OBJETO 1 31) "0" (substr OBJETO 33)))
            (SETQ LISTADCLOBJ (ACTUALIZABD LISTADCLOBJ 74 EVENTOX LINEAFIN))
            (dibujaelem LINEAFIN)
          )
        )
      )
    )
    (SETQ CONTDESP (1+ CONTDESP))
  )
)

(DEFUN DESPULSA2 (BOTON)
  (SETQ CONTDESP 3)
  (REPEAT 3
    (IF (/= CONTDESP (ATOI (SUBSTR BOTON 5 1)))
      (PROGN
        (SETQ EVENTOX (STRCAT "ACC0" (ITOA CONTDESP)))
        (SETQ OBJETO (BUSOBJBD LISTADCLOBJ 74 EVENTOX))
        (setq statusobj (SUBSTR OBJETO 32 1))
        (IF (= statusobj "1") 
          (PROGN
            (setq LINEAFIN (strcat (substr OBJETO 1 31) "0" (substr OBJETO 33)))
            (SETQ LISTADCLOBJ (ACTUALIZABD LISTADCLOBJ 74 EVENTOX LINEAFIN))
            (dibujaelem LINEAFIN)
          )
        )
      )
    )
    (SETQ CONTDESP (1+ CONTDESP))
  )
)

(DEFUN DESPULSA3 (BOTON)
  (SETQ CONTDESP 1)
  (REPEAT 9
    (if (or (= contdesp 1) (= contdesp 2)) (setq CONTDESPf contdesp))
    (if (and (>= contdesp 3) (<= contdesp 8)) (setq CONTDESPf (+ contdesp 3)))
    (if (> contdesp 8) (setq CONTDESPf 14))
    (IF (/= CONTDESPf (ATOI (SUBSTR BOTON 4 2)))
      (PROGN
        (if (<= contdesp 6)
          (SETQ EVENTOX (STRCAT "ACC0" (ITOA CONTDESPf)))
          (SETQ EVENTOX (STRCAT "ACC" (ITOA CONTDESPf)))
        )
        (SETQ OBJETO (BUSOBJBD LISTADCLOBJ 74 EVENTOX))
        (setq statusobj (SUBSTR OBJETO 32 1))
        (IF (= statusobj "1") 
          (PROGN
            (if (= EVENTOX "ACC01")
              (progn
                (desactiva2 "colorgrf1")
              )
            )
            (if (= EVENTOX "ACC02")
              (progn
                (desactiva2 "colorgrf2")
              )
            )
            (if (= EVENTOX "ACC06")
              (progn
                (desactiva2 "rcmobj")
              )
            )
            (if (= EVENTOX "ACC07")
              (progn
                (desactiva2 "rctobj")
              )
            )
            (if (= EVENTOX "ACC08")
              (progn
                (desactiva2 "vmobj")
              )
            )
            (if (= EVENTOX "ACC09")
              (progn
                (desactiva2 "vmiobj")
              )
            )
            (if (= EVENTOX "ACC10")
              (progn
                (desactiva2 "vmeobj")
              )
            )
            (if (= EVENTOX "ACC11")
              (progn
                (desactiva2 "sumobj")
              )
            )
            (if (= EVENTOX "ACC14")
              (progn
                (SETQ OBJETOEV14 (BUSOBJBD LISTADCLOBJ2 274 "SOBRE1"))
;                (ALERT (substr OBJETOEV14 255 2))
                (SETQ L1ST (substr OBJETOEV14 255 2))
                (SETQ OBJETOEV14 (BUSOBJBD LISTADCLOBJ2 274 "SOBRE2"))
;                (ALERT (substr OBJETOEV14 255 4))
                (SETQ L2ST (substr OBJETOEV14 255 4))
                (SETQ OBJETOEV14 (BUSOBJBD LISTADCLOBJ2 274 "SOBRE3"))
;                (ALERT (substr OBJETOEV14 255 3))
                (SETQ L3ST (substr OBJETOEV14 255 3))
                (SETQ VARGRF2 (STRCAT (SUBSTR VARGRF2 1 35) L1ST L2ST L3ST (SUBSTR VARGRF2 45 1)))
                (desactiva2 "sobobj")
              )
            )
            (setq LINEAFIN (strcat (substr OBJETO 1 31) "0" (substr OBJETO 33)))
            (SETQ LISTADCLOBJ (ACTUALIZABD LISTADCLOBJ 74 EVENTOX LINEAFIN))
            (dibujaelem LINEAFIN)
          )
        )
      )
    )
    (SETQ CONTDESP (1+ CONTDESP))
  )
)

(defun investigobj (objetor)
  (if (OR (AND (= (SUBSTR OBJETOR 1 6) "DATOSF") (= (STRLEN OBJETOR) 7)) (= OBJETOR "CONSIST1") (= OBJETOR "CONSIST2") (= OBJETOR "LLENA1") (= OBJETOR "LLENA2") (= OBJETOR "RESUM1"))
    (SETQ TIPOOBJR 2)
    (SETQ TIPOOBJR 1)
  )
  (IF (= TIPOOBJR 2)
    (PROGN
      (SETQ OBJETO (BUSOBJBD LISTADCLOBJ2 274 objetor))
      (setq statusobjES (SUBSTR OBJETO 255 20))
      (SETQ NDATOPULSA (NPULSADO statusobjES))
    )
    (PROGN
      (SETQ OBJETO (BUSOBJBD LISTADCLOBJ 74 objetor))
      (setq RESULTADOI (SUBSTR OBJETO 32 1))
    )
  )
  (IF (AND (= (SUBSTR OBJETOR 1 6) "DATOSF") (= (STRLEN OBJETOR) 7))
    (PROGN
      (IF (= OBJETOR "DATOSF1")
        (PROGN
          (IF (= NDATOPULSA 1) (SETQ RESULTADOI "AN"))
          (IF (= NDATOPULSA 2) (SETQ RESULTADOI "ME"))
          (IF (= NDATOPULSA 3) (SETQ RESULTADOI "ST"))
        )
      )
      (IF (OR (= OBJETOR "DATOSF2") (= OBJETOR "DATOSF4") (= OBJETOR "DATOSF5"))
        (SETQ RESULTADOI NDATOPULSA)
      )
      (IF (= OBJETOR "DATOSF3")
        (PROGN
          (IF (= NDATOPULSA 1) (SETQ RESULTADOI "MA"))
          (IF (= NDATOPULSA 2) (SETQ RESULTADOI "ME"))
          (IF (= NDATOPULSA 3) (SETQ RESULTADOI "MI"))
          (IF (= NDATOPULSA 4) (SETQ RESULTADOI "TO"))
        )
      )
    )
  )
  (IF (AND (/= (SUBSTR OBJETOR 1 6) "DATOSF") (= TIPOOBJR 2))
    (SETQ RESULTADOI NDATOPULSA)
  )
  (SETQ RESULTADOI RESULTADOI)
)

(defun v92 ()
  (start_image "imagen")
  (DESTA2 vzoom)
  (setq nest (1+ nest))
  (if (> nest (+ num2 num3)) (setq nest 1))
  (dpuntero2 vzoom)
  (end_image)
)

(defun v102 ()
  (start_image "imagen")
  (DESTA2 vzoom)
  (if (< 1 nest) 
   (setq nest (1- nest))
   (setq nest (+ num2 num3))
  )
  (dpuntero2 vzoom)
  (end_image)
)

(defun estdefinitiva2 (estbuscada);casa
  (setq decision "")
  (if (> estbuscada num2)
    (progn
      (setq nciclos (/ (strlen ESTACFINALE2) 5))
      (setq varanaliz ESTACFINALE2)
    )
    (progn
      (setq nciclos (/ (strlen ESTACFINALC2) 5))
      (setq varanaliz ESTACFINALC2)
    )
  )
  (setq contadore 1)
   (repeat nciclos
    (setq numero (atoi (substr varanaliz (1+ (* 5 (1- contadore))) 5)))
    (if (= numero estbuscada) (setq decision "S"))
    (setq contadore (1+ contadore))
  )
  (if (= decision "S")
    (setq decision "S")
    (setq decision "N")
  )
)

(defun estdefinitivab2 (estbuscada);casa
  (if (> estbuscada num2)
    (progn
      (setq nciclos (/ (strlen ESTACFINALE2) 5))
      (setq varanaliz ESTACFINALE2)
    )
    (progn
      (setq nciclos (/ (strlen ESTACFINALC2) 5))
      (setq varanaliz ESTACFINALC2)
    )
  )
  (setq contadore 1)
  (repeat nciclos
    (setq numero (atoi (substr varanaliz (1+ (* 5 (1- contadore))) 5)))
    (if (= numero estbuscada) (setq decision contadore))
    (setq contadore (1+ contadore))
  )
  (if (= nciclos 1)
    (if (> estbuscada num2)
      (setq ESTACFINALE2 "")
      (setq ESTACFINALC2 "")
    )
    (if (> estbuscada num2)
      (setq ESTACFINALE2 (strcat (substr varanaliz 1 (* 5 (1- decision))) (substr varanaliz (+ 6 (* 5 (1- decision))))))
      (setq ESTACFINALC2 (strcat (substr varanaliz 1 (* 5 (1- decision))) (substr varanaliz (+ 6 (* 5 (1- decision))))))
    )
  )
)

(defun nestaccX (nest)
  (setq resultado nil)
  (setq num2 0) 
  (if (= eclicom "1")
    (progn
      (SETQ IDEST 1)
      (while idest
        (setq idest (cdr (assoc num2 MATRIZESTD)))
        (setq num2 (1+ num2))
      )
    )
  )
  (setq num3 0) 
  (if (= eeric "1")
    (progn
      (SETQ IDEST 1)
      (while idest
        (setq idest (cdr (assoc num3 MATRIZEST2D)))
        (setq num3 (1+ num3))
      )
    )
  )
  (if (/= num2 0) (setq num2 (1- num2)))
  (if (/= num3 0) (setq num3 (1- num3)))
  (setq ntest (+ num2 num3))
  (if (and (> nest ntest) (= eclicom "1") (= eeric "1"))
    (setq resultado "no")
  )
  (if (and (<= nest ntest) (= eclicom "1") (= eeric "1"))
    (progn
      (if (<= nest num2)
        (setq resultado (cdr (assoc (1- nest) MATRIZESTD)))
        (setq resultado (cdr (assoc (- nest num2 1) MATRIZEST2D)))
      )
    )
  )
  (if (and (> nest ntest) (= eeric "1") (/= eclicom "1"))
    (setq resultado "no")
  )
  (if (and (<= nest ntest) (= eeric "1") (/= eclicom "1"))
    (setq resultado (cdr (assoc (1- nest) MATRIZEST2D)))
  )
  (if (and (> nest ntest) (/= eeric "1") (= eclicom "1"))
    (setq resultado "no")
  )
  (if (and (<= nest ntest) (/= eeric "1") (= eclicom "1"))
    (setq resultado (cdr (assoc (1- nest) MATRIZESTD)))
  )
  (print resultado)
)

(defun v1 ()
  (setq btnr (get_tile "utlr"))
  (if (<= nestx num2)
    (setq elm (assoc nestx matrizllenacrn))
    (setq elm (assoc (- nestx num2) matrizllenaern))
  )
  (SETQ CLVEST (CAR (CDR elm)))
  (if (<= nest num2)
    (setq elmb (assoc nest matrizllenacrn))
    (setq elmb (assoc (- nest num2) matrizllenaern))
  )
  (SETQ CLVESTb (CAR (CDR elmb)))
  (setq dbase (caddr elmb))
  (if (and (not (wcmatch dbase (strcat "*" clvest "*"))) (= btnr "1")) ;si no esta seleccionado, para activarlo
   (progn
    (SETQ CUEVER 1)
    (SETQ matrizprov NIL)
    (if (<= nest num2)
     (progn
      (repeat nestfc
        (setq elmp (assoc cuever matrizllenacrn))
        (SETQ CLVESTp (CAR (CDR elmp)))
        (if (= CLVESTb CLVESTp)
          (progn
           (setq dbase (strcat dbase clvest))
           (setq verpol (list clvestb dbase))         
           (setq CONCATENADO (list (cons cuever verpol)))
           (setq matrizprov (append matrizprov CONCATENADO))
          );progn
          (setq matrizprov (append matrizprov (list elmp)))
        );if
        (SETQ CUEVER (1+ CUEVER))
      );repeat
      (setq matrizllenacrn matrizprov)
     )
     (progn
      (repeat nestfe
        (setq elmp (assoc cuever matrizllenaern))
        (SETQ CLVESTp (CAR (CDR elmp)))
        (print clvestb)
        (print clvestp)
        (if (= CLVESTb CLVESTp)
          (progn
           (setq dbase (strcat dbase clvest))
           (setq verpol (list clvestb dbase))
           (setq CONCATENADO (list (cons cuever verpol)))
           (setq matrizprov (append matrizprov CONCATENADO))
          );progn
          (setq matrizprov (append matrizprov (list elmp)))
        );if
        (SETQ CUEVER (1+ CUEVER))
      );repeat
      (setq matrizllenaern matrizprov)
     );progn
    );if
   );progn
  );if
  (if (and (wcmatch dbase (strcat "*" clvest "*")) (= btnr "0")); si esta seleccionado para desactivarlo
   (progn
    (SETQ CUEVER 1)
    (SETQ matrizprov NIL)
    (if (<= nest num2)
     (progn
       (repeat nestfc
         (setq elmp (assoc cuever matrizllenacrn))
         (SETQ CLVESTp (CAR (CDR elmp)))
         (if (= CLVESTb CLVESTp)
           (progn
            (setq dbase (vl-string-subst "" clvest dbase))
            (setq verpol (list clvestb dbase))         
            (setq CONCATENADO (list (cons cuever verpol)))
            (setq matrizprov (append matrizprov CONCATENADO))
           );progn
           (setq matrizprov (append matrizprov (list elmp)))
         );if
         (SETQ CUEVER (1+ CUEVER))
       );repeat
       (setq matrizllenacrn matrizprov)
     );progn
     (progn
       (repeat nestfe
         (setq elmp (assoc cuever matrizllenaern))
         (SETQ CLVESTp (CAR (CDR elmp)))
         (if (= CLVESTb CLVESTp)
           (progn
            (setq dbase (vl-string-subst "" clvest dbase))
            (setq verpol (list clvestb dbase))         
            (setq CONCATENADO (list (cons cuever verpol)))
            (setq matrizprov (append matrizprov CONCATENADO))
           );progn
           (setq matrizprov (append matrizprov (list elmp)))
         );if
         (SETQ CUEVER (1+ CUEVER))
       );repeat
       (setq matrizllenaern matrizprov)
     );progn
    );if
   );progn
  );if
)

(defun v2 ()
  (setq btnr (get_tile "utlp"))
  (if (<= nestx num2)
    (setq elm (assoc nestx matrizllenacpa))
    (setq elm (assoc (- nestx num2) matrizllenaepa))
  )
  (SETQ CLVEST (CAR (CDR elm)))
  (if (<= nest num2)
    (setq elmb (assoc nest matrizllenacpa))
    (setq elmb (assoc (- nest num2) matrizllenaepa))
  )
  (SETQ CLVESTb (CAR (CDR elmb)))
  (setq dbase (caddr elmb))
  (if (and (not (wcmatch dbase (strcat "*" clvest "*"))) (= btnr "1")) ;si no esta seleccionado, para activarlo
   (progn
    (SETQ CUEVER 1)
    (SETQ matrizprov NIL)
    (if (<= nest num2)
     (progn
      (repeat nestfc
        (setq elmp (assoc cuever matrizllenacpa))
        (SETQ CLVESTp (CAR (CDR elmp)))
        (if (= CLVESTb CLVESTp)
          (progn
           (setq dbase (strcat dbase clvest))
           (setq verpol (list clvestb dbase))         
           (setq CONCATENADO (list (cons cuever verpol)))
           (setq matrizprov (append matrizprov CONCATENADO))
          );progn
          (setq matrizprov (append matrizprov (list elmp)))
        );if
        (SETQ CUEVER (1+ CUEVER))
      );repeat
      (setq matrizllenacpa matrizprov)
     )
     (progn
      (repeat nestfe
        (setq elmp (assoc cuever matrizllenaepa))
        (SETQ CLVESTp (CAR (CDR elmp)))
        (print clvestb)
        (print clvestp)
        (if (= CLVESTb CLVESTp)
          (progn
           (setq dbase (strcat dbase clvest))
           (setq verpol (list clvestb dbase))
           (setq CONCATENADO (list (cons cuever verpol)))
           (setq matrizprov (append matrizprov CONCATENADO))
          );progn
          (setq matrizprov (append matrizprov (list elmp)))
        );if
        (SETQ CUEVER (1+ CUEVER))
      );repeat
      (setq matrizllenaepa matrizprov)
     );progn
    );if
   );progn
  );if
  (if (and (wcmatch dbase (strcat "*" clvest "*")) (= btnr "0")); si esta seleccionado para desactivarlo
   (progn
    (SETQ CUEVER 1)
    (SETQ matrizprov NIL)
    (if (<= nest num2)
     (progn
       (repeat nestfc
         (setq elmp (assoc cuever matrizllenacpa))
         (SETQ CLVESTp (CAR (CDR elmp)))
         (if (= CLVESTb CLVESTp)
           (progn
            (setq dbase (vl-string-subst "" clvest dbase))
            (setq verpol (list clvestb dbase))         
            (setq CONCATENADO (list (cons cuever verpol)))
            (setq matrizprov (append matrizprov CONCATENADO))
           );progn
           (setq matrizprov (append matrizprov (list elmp)))
         );if
         (SETQ CUEVER (1+ CUEVER))
       );repeat
       (setq matrizllenacpa matrizprov)
     );progn
     (progn
       (repeat nestfe
         (setq elmp (assoc cuever matrizllenaepa))
         (SETQ CLVESTp (CAR (CDR elmp)))
         (if (= CLVESTb CLVESTp)
           (progn
            (setq dbase (vl-string-subst "" clvest dbase))
            (setq verpol (list clvestb dbase))         
            (setq CONCATENADO (list (cons cuever verpol)))
            (setq matrizprov (append matrizprov CONCATENADO))
           );progn
           (setq matrizprov (append matrizprov (list elmp)))
         );if
         (SETQ CUEVER (1+ CUEVER))
       );repeat
       (setq matrizllenaepa matrizprov)
     );progn
    );if
   );progn
  );if
)

(defun v3 ()
  (setq btnr (get_tile "utlus"))
  (if (<= nestx num2)
    (setq elm (assoc nestx matrizllenacmu))
    (setq elm (assoc (- nestx num2) matrizllenaemu))
  )
  (SETQ CLVEST (CAR (CDR elm)))
  (if (<= nest num2)
    (setq elmb (assoc nest matrizllenacmu))
    (setq elmb (assoc (- nest num2) matrizllenaemu))
  )
  (SETQ CLVESTb (CAR (CDR elmb)))
  (setq dbase (caddr elmb))
  (if (and (not (wcmatch dbase (strcat "*" clvest "*"))) (= btnr "1")) ;si no esta seleccionado, para activarlo
   (progn
    (SETQ CUEVER 1)
    (SETQ matrizprov NIL)
    (if (<= nest num2)
     (progn
      (repeat nestfc
        (setq elmp (assoc cuever matrizllenacmu))
        (SETQ CLVESTp (CAR (CDR elmp)))
        (if (= CLVESTb CLVESTp)
          (progn
           (setq dbase (strcat dbase clvest))
           (setq verpol (list clvestb dbase))         
           (setq CONCATENADO (list (cons cuever verpol)))
           (setq matrizprov (append matrizprov CONCATENADO))
          );progn
          (setq matrizprov (append matrizprov (list elmp)))
        );if
        (SETQ CUEVER (1+ CUEVER))
      );repeat
      (setq matrizllenacmu matrizprov)
     )
     (progn
      (repeat nestfe
        (setq elmp (assoc cuever matrizllenaemu))
        (SETQ CLVESTp (CAR (CDR elmp)))
        (print clvestb)
        (print clvestp)
        (if (= CLVESTb CLVESTp)
          (progn
           (setq dbase (strcat dbase clvest))
           (setq verpol (list clvestb dbase))
           (setq CONCATENADO (list (cons cuever verpol)))
           (setq matrizprov (append matrizprov CONCATENADO))
          );progn
          (setq matrizprov (append matrizprov (list elmp)))
        );if
        (SETQ CUEVER (1+ CUEVER))
      );repeat
      (setq matrizllenaemu matrizprov)
     );progn
    );if
   );progn
  );if
  (if (and (wcmatch dbase (strcat "*" clvest "*")) (= btnr "0")); si esta seleccionado para desactivarlo
   (progn
    (SETQ CUEVER 1)
    (SETQ matrizprov NIL)
    (if (<= nest num2)
     (progn
       (repeat nestfc
         (setq elmp (assoc cuever matrizllenacmu))
         (SETQ CLVESTp (CAR (CDR elmp)))
         (if (= CLVESTb CLVESTp)
           (progn
            (setq dbase (vl-string-subst "" clvest dbase))
            (setq verpol (list clvestb dbase))         
            (setq CONCATENADO (list (cons cuever verpol)))
            (setq matrizprov (append matrizprov CONCATENADO))
           );progn
           (setq matrizprov (append matrizprov (list elmp)))
         );if
         (SETQ CUEVER (1+ CUEVER))
       );repeat
       (setq matrizllenacmu matrizprov)
     );progn
     (progn
       (repeat nestfe
         (setq elmp (assoc cuever matrizllenaemu))
         (SETQ CLVESTp (CAR (CDR elmp)))
         (if (= CLVESTb CLVESTp)
           (progn
            (setq dbase (vl-string-subst "" clvest dbase))
            (setq verpol (list clvestb dbase))         
            (setq CONCATENADO (list (cons cuever verpol)))
            (setq matrizprov (append matrizprov CONCATENADO))
           );progn
           (setq matrizprov (append matrizprov (list elmp)))
         );if
         (SETQ CUEVER (1+ CUEVER))
       );repeat
       (setq matrizllenaemu matrizprov)
     );progn
    );if
   );progn
  );if
)

(defun revisasel ()
  (if (<= nestx num2)
    (setq elm (assoc nestx matrizllenacrn))
    (setq elm (assoc (- nestx num2) matrizllenaern))
  )
  (SETQ CLVEST (CAR (CDR elm)))
  (if (<= nest num2)
    (setq elmb (assoc nest matrizllenacrn))
    (setq elmb (assoc (- nest num2) matrizllenaern))
  )
  (SETQ CLVESTb (CAR (CDR elmb)))
  (setq dbase (caddr elmb))
  (if (wcmatch dbase (strcat "*" clvest "*"))
    (set_tile "utlr" "1")
    (set_tile "utlr" "0")
  )
  (if (<= nestx num2)
    (setq elm2 (assoc nestx matrizllenacpa))
    (setq elm2 (assoc (- nestx num2) matrizllenaepa))
  )
  (SETQ CLVEST (CAR (CDR elm2)))
  (if (<= nest num2)
    (setq elmb (assoc nest matrizllenacpa))
    (setq elmb (assoc (- nest num2) matrizllenaepa))
  )
  (SETQ CLVESTb (CAR (CDR elmb)))
  (setq dbase (caddr elmb))
  (if (wcmatch dbase (strcat "*" clvest "*"))
    (set_tile "utlp" "1")
    (set_tile "utlp" "0")
  )
  (if (<= nestx num2)
    (setq elm2 (assoc nestx matrizllenacmu))
    (setq elm2 (assoc (- nestx num2) matrizllenaemu))
  )
  (SETQ CLVEST (CAR (CDR elm2)))
  (if (<= nest num2)
    (setq elmb (assoc nest matrizllenacmu))
    (setq elmb (assoc (- nest num2) matrizllenaemu))
  )
  (SETQ CLVESTb (CAR (CDR elmb)))
  (setq dbase (caddr elmb))
  (if (wcmatch dbase (strcat "*" clvest "*"))
    (set_tile "utlus" "1")
    (set_tile "utlus" "0")
  )
)
