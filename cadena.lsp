(defun cottopo (nume)
  (setq texto (rtos nume 2 0))
  (setq kilm 0)
  (if (= nume 0)
    (prin1 (setq resto "000"))
  )
  (if (> nume 9)
    (setq resto (strcat "0" texto))
  )
  (if (> nume 99)
   (setq resto texto)
  )
  (if (> nume 999)
    (progn
       (setq num1 (substr texto 1 1))
       (setq resto (substr texto 2 3))
    )
    (setq num1 "0")
  )
  (if (> nume 9999)
    (progn
      (setq num1 (substr texto 1 2))
      (setq resto (substr texto 3 3))
    )
  )
  (setq nuetex (strcat num1 "+" resto))
)


(defun c:CADENA ()
  (setq CA (getstring "Capa a localizar: "))
  (write-line "Cadenamientos segun orden de creación: ")
  (setq IC (getreal " Inicio de Cadenamiento con numero: "))
  (setq IN (getreal " Incremento: "))
  (setq e (entnext))
  (setq cadena IC)
  (while e
    (if (= "TEXT" (cdr (assoc 0 (entget e))))
      (progn
        (if (= (strcase CA) (cdr (assoc 8 (entget e))))
          (progn
            (setq cadd (rtos cadena 2 0))
            (setq nte (cottopo (atof cadd)))
            (entmod (subst (cons 1 nte) (assoc 1 (entget e)) (entget e)))
            (setq cadena (+ cadena IN))
          )
        )
      )
    )
    (setq e (entnext e))
  )
)
