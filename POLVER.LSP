(defun verticeSURF (poli nov)
  (setq listap (entget poli))
  (setq nver 0)
  (setq salir "N")
  (while (= salir "N")
    (setq sublisp (car listap))
    (if (= 10 (car sublisp))
      (progn
        (setq punto (cdr sublisp))   
        (setq nver (+ nver 1))
      )
    )
    (setq listap (cdr listap))
    (if listap
      (setq salir "N")
      (setq salir "S")
    )
    (if (= nov nver)
      (setq salir "S")
    )
  )
  (if (not listap)
    (setq punto nil)
  )
  (setq punto punto)
)

(DEFUN C:POLVER1 ()
  (SETQ OP (EXLAYER "AUTOMATICO"))
  (IF (= OP "N")
    (COMMAND "-LAYER" "N" "AUTOMATICO" "")
  )
  (setq lin (car (entsel "\n Selecciona la polylinea a procesar: ")))
  (SETQ ARRANQUE 1000)
  (while (/= "LWPOLYLINE" (cdr (assoc 0 (entget lin))))
      (if (/= "LWPOLYLINE" (cdr (assoc 0 (entget lin))))
        (progn   
          (alert "\nEl objeto debe ser polylinea ")
          (setq lin (car (entsel "\n Selecciona objeto: ")))
        )
      )
  )
  (SETQ TIPBD (GETSTRING "\n TIPO DE ARCHIVO DE SALIDA (Surfer/X-y-z-c-n/sAuce/Dist-azimut/Gogle pantalla) (S/X/A/D/G):"))
  (IF (= (STRCASE TIPBD) "D")
   (PROGN
    (C:LIBRERIA "DECIMALTOSEXAGESIMAL2")
    (setq arcdes (getfiled "ARCHIVO DE Descarga" "*." "csv" 19))
    (setq f 0)
    (SETQ VER1 "")
    (while ver1
       (setq f (1+ f))
       (SETQ VER1 (verticeSURF lin f)) 
    )
    (setq f (1- f))
    (SETQ f1 (OPEN arcdes "w"))
    (setq J 1)
    (setq elevs "1")
    (setq CODEs "V")
    (SETQ VER2 (verticeSURF lin 1))
    (setq verh ver2)
    (REPEAT (1- f)
       (setq J (1+ J))
       (PRINT J)
       (SETQ VER1 (verticeSURF lin J))
       (setq distancia (distance ver2 ver1))
       (setq angulo (angle ver2 ver1))
       (setq angulo (/ (* angulo 180) 3.1415926535897932384626433832795))
       (setq angulo (- 450 angulo))
       (if (> angulo 359.999999999999999999) (setq angulo (- angulo 360)))
       (setq angulo (DECSEXA angulo))
       (IF (/= VER1 NIL)
         (progn
           (write-line (strcat (rtos distancia 2 3) "," angulo) F1)
           (setq ver2 ver1)
         )
       )
    )
    (setq distancia (distance ver2 verh))
    (setq angulo (angle ver2 verh))
    (setq angulo (/ (* angulo 180) 3.1415926535897932384626433832795))
    (setq angulo (- 450 angulo))
    (if (> angulo 359.999999999999999999) (setq angulo (- angulo 360)))
    (setq angulo (DECSEXA angulo))
    (write-line (strcat (rtos distancia 2 3) "," angulo) F1)
   )
  )
  (IF (= (STRCASE TIPBD) "G")
    (progn
      (C:LIBRERIA "UTM-GEO")
      (if (= zonah nil) (setq zonah "00"))
      (SETQ zonah1 (GETSTRING (strcat "\n ZONA UTM HORARIA <" zonah ">:")))
      (IF (/= zonah1 "")
        (SETQ zonah zonah1)
      )
      (setq lvert "")
      (setq f 0)
      (SETQ VER1 "")
      (while ver1
         (setq f (1+ f))
         (SETQ VER1 (verticeSURF lin f)) 
      )
      (setq f (1- f))
      (setq J 0)
      (REPEAT F
         (setq J (1+ J))
         (PRINT J)
         (SETQ VER1 (verticeSURF lin J))
         (IF (/= VER1 NIL)
           (progn
             (setq pgeo (UTM-GEO ver1 (ATOI ZONAH)))
             (setq lvert (strcat lvert (rtos (car pgeo) 2 13) "," (rtos (car (cdr pgeo)) 2 14) ",0 "))
           )
         )
      )
      (print lvert)
    )
  )
  (IF (= (STRCASE TIPBD) "S")
   (PROGN
    (setq arcdes (getfiled "ARCHIVO DE Descarga" "*." "bln" 19))
    (setq f 0)
    (SETQ VER1 "")
    (while ver1
       (setq f (1+ f))
       (SETQ VER1 (verticeSURF lin f)) 
    )
    (setq f (1- f))
    (SETQ f1 (OPEN arcdes "w"))
    (WRITE-LINE (STRCAT (ITOA F) ", 0" ) F1)
    (setq J 0)
    (REPEAT F
       (setq J (1+ J))
       (PRINT J)
       (SETQ VER1 (verticeSURF lin J))
       (IF (/= VER1 NIL)
         (write-line (strcat (rtos (car ver1) 2 3) "," (rtos (car (cdr ver1)) 2 3)) F1)
       )
    )
   )
  )
  (IF (= (STRCASE TIPBD) "X")
   (progn
    (setq arcdes (getfiled "ARCHIVO DE Descarga" "*." "csv" 19))
    (SETQ f1 (OPEN arcdes "w"))
  (SETQ OPBUS (GETSTRING "\n Realizar busqueda de puntos (S/N) <S> :"))
   (if (= opbus "")
    (setq opbus "S")
   )
   (if (= (STRCASE opbus) "S")
    (PROGN
    (MPUN LIN)
    (SETQ J 0)
    (SETQ VER1 "")
    (WHILE VER1
       (setq J (1+ J))
       (PRINT J)
       (SETQ VER1 (verticeSURF lin J))
       (IF (/= VER1 NIL)
        (PROGN
         (setq gnupo (ssget "C" (suma VER1 0.01 0.01) (suma VER1 -0.01 -0.01)))
         (setq conta 0)
         (setq enco 0)
         (while (/= conta (sslength gnupo))
           (setq nnupo (ssname gnupo conta))
           (SETQ PV (cdr (assoc 10 (entget nnupo))))
           (SETQ XV (CAR PV))
           (SETQ YV (CADR PV))
           (SETQ X1 (CAR VER1))
           (SETQ Y1 (CADR VER1))
           (if (OR (= "PUN2" (cdr (assoc 2 (entget nnupo)))) (= "PUNTO" (cdr (assoc 2 (entget nnupo)))))
             (IF (AND (= (RTOS XV 2 2) (RTOS X1 2 2)) (= (RTOS YV 2 2) (RTOS Y1 2 2)))
               (progn
                 (setq enco 1)
                 (setq conta (- (sslength gnupo) 1))
               )
             )
           )
           (setq conta (+ conta 1))
         )
         (if (= enco 1)
           (progn
             (setq CODES (BUSATR nnupo "CODE"))
             (setq ELEVS (BUSATR nnupo "ELEV"))
             (setq PUNTOS (BUSATR nnupo "PUNTO"))
;             (setq numpun (cdr (assoc 1 (entget atr1))))
;             (setq espu (cdr (assoc 41 (entget nnupo))))
           )
           (progn
            (ALERT "NO SE ENCONTRO BLOCK EN UN VERTICE")
            (COMMAND "VIEW" "S" "MSA")
            (COMMAND "ZOOM" "C" VER1 "10")
            (COMMAND "CIRCLE" VER1 ".1")
            (SETQ PROVE (ENTLAST))
            (setQ OPT2 (GETSTRING "DESEAS /I-nsertar/S-eleccionar/ EL BLOCK (I/S) <I> :"))
            (IF (= "CIRCLE" (cdr (assoc 0 (ENTGET PROVE))))
              (COMMAND "ERASE" PROVE "")
            )
            (COMMAND "VIEW" "R" "MSA")
            (IF (= OPT2 "")
               (SETQ OPT2 "I") 
            )
            (IF (= (STRCASE OPT2) "I")
              (PROGN
               (setQ OPT3 (GETREAL (STRCAT "NUMERO DE PUNTO A INSERTAR <"(RTOS (1+ ARRANQUE) 2 0) "> :")))
               (IF (/= OPT3 NIL)
                  (SETQ ARRANQUE (1- OPT3)) 
               )                      
               (command "INSERT" (STRCAT RUTA "BLOCKS\\PUNTO") VER1 "" "" "" (rtos (+ arranque 1) 2 0)  "AUTOMATICO" "" "")
               (command "CHANGE" (entlast) "" "P" "LA" "AUTOMATICO" "")
               (setq arranque (+ arranque 1))
               (setq numpun (rtos arranque 2 0))
              )
              (PROGN 
               (setq PROVE (car (entsel "Selecciona el bloque a MOVER: ")))
               (command "MOVE" PROVE "" (cdr (assoc 10 (entget PROVE))) VER1)
              ) 
             )
            (SETQ PUNTOS (rtos arranque 2 0))
            (SETQ CODES "AUTOMATICO")
            (SETQ ELEVS "0")
            )
           )
         )
       )
       (IF (= ELEVS NIL) (SETQ ELEVS "1"))
       (IF (= CODES NIL) (SETQ CODES "X"))
       (IF (= PUNTOS NIL) (SETQ PUNTOS "N"))
       (IF (/= VER1 NIL)
         (write-line (strcat (rtos (car ver1) 2 3) "," (rtos (car (cdr ver1)) 2 3) "," ELEVS "," PUNTOS "," CODES) F1)
       )
    )
    )
   )
   (if (= (strcase opbus) "N")
    (PROGN
      (setq f 0)
      (SETQ VER1 "")
      (while ver1
         (setq f (1+ f))
         (SETQ VER1 (verticeSURF lin f)) 
      )
      (setq f (1- f))
      (SETQ f1 (OPEN arcdes "w"))
      (setq J 0)
      (setq elevs "1")
      (setq CODEs "V")
      (REPEAT F
         (setq J (1+ J))
         (PRINT J)
         (SETQ VER1 (verticeSURF lin J))
         (IF (/= VER1 NIL)
           (write-line (strcat (rtos (car ver1) 2 3) "," (rtos (car (cdr ver1)) 2 3) "," ELEVS "," (ITOA J) "," CODES) F1)
         )
      )
    )
   )
   )
  )
  (IF (= (STRCASE TIPBD) "A")
   (progn
    (setq arcdes (getfiled "ARCHIVO DE Descarga" "*." "cgp" 19))
    (SETQ f1 (OPEN arcdes "w"))
    (SETQ f2 (OPEN (strcat (substr arcdes 1 (- (strlen arcdes) 4)) ".DAT") "w"))
    (write-line "INICIO" F2)
  (SETQ OPBUS (GETSTRING "\n Realizar busqueda de puntos (S/N) <S> :"))
   (if (= opbus "")
    (setq opbus "S")
   )
   (if (= (STRCASE opbus) "S")
    (PROGN
    (MPUN LIN)
    (SETQ J 0)
    (SETQ VER1 "")
    (WHILE VER1
       (setq J (1+ J))
       (PRINT J)
       (SETQ VER1 (verticeSURF lin J))
       (IF (/= VER1 NIL)
        (PROGN
         (setq gnupo (ssget "C" (suma VER1 0.01 0.01) (suma VER1 -0.01 -0.01)))
         (setq conta 0)
         (setq enco 0)
         (while (/= conta (sslength gnupo))
           (setq nnupo (ssname gnupo conta))
           (SETQ PV (cdr (assoc 10 (entget nnupo))))
           (SETQ XV (CAR PV))
           (SETQ YV (CADR PV))
           (SETQ X1 (CAR VER1))
           (SETQ Y1 (CADR VER1))
           (if (OR (= "PUN2" (cdr (assoc 2 (entget nnupo)))) (= "PUNTO" (cdr (assoc 2 (entget nnupo)))))
             (IF (AND (= (RTOS XV 2 2) (RTOS X1 2 2)) (= (RTOS YV 2 2) (RTOS Y1 2 2)))
               (progn
                 (setq enco 1)
                 (setq conta (- (sslength gnupo) 1))
               )
             )
           )
           (setq conta (+ conta 1))
         )
         (if (= enco 1)
           (progn
             (setq CODES (BUSATR nnupo "CODE"))
             (setq ELEVS (BUSATR nnupo "ELEV"))
             (setq PUNTOS (BUSATR nnupo "PUNTO"))
;             (setq numpun (cdr (assoc 1 (entget atr1))))
;             (setq espu (cdr (assoc 41 (entget nnupo))))
           )
           (progn
            (ALERT "NO SE ENCONTRO BLOCK EN UN VERTICE")
            (COMMAND "VIEW" "S" "MSA")
            (COMMAND "ZOOM" "C" VER1 "10")
            (COMMAND "CIRCLE" VER1 ".1")
            (SETQ PROVE (ENTLAST))
            (setQ OPT2 (GETSTRING "DESEAS /I-nsertar/S-eleccionar/ EL BLOCK (I/S) <I> :"))
            (IF (= "CIRCLE" (cdr (assoc 0 (ENTGET PROVE))))
              (COMMAND "ERASE" PROVE "")
            )
            (COMMAND "VIEW" "R" "MSA")
            (IF (= OPT2 "")
               (SETQ OPT2 "I") 
            )
            (IF (= (STRCASE OPT2) "I")
              (PROGN
               (setQ OPT3 (GETREAL (STRCAT "NUMERO DE PUNTO A INSERTAR <"(RTOS (1+ ARRANQUE) 2 0) "> :")))
               (IF (/= OPT3 NIL)
                  (SETQ ARRANQUE (1- OPT3)) 
               )                      
               (command "INSERT" (STRCAT RUTA "BLOCKS\\PUNTO") VER1 "" "" "" (rtos (+ arranque 1) 2 0)  "AUTOMATICO" "" "")
               (command "CHANGE" (entlast) "" "P" "LA" "AUTOMATICO" "")
               (setq arranque (+ arranque 1))
               (setq numpun (rtos arranque 2 0))
              )
              (PROGN 
               (setq PROVE (car (entsel "Selecciona el bloque a MOVER: ")))
               (command "MOVE" PROVE "" (cdr (assoc 10 (entget PROVE))) VER1)
              ) 
             )
            (SETQ PUNTOS (rtos arranque 2 0))
            (SETQ CODES "AUTOMATICO")
            (SETQ ELEVS "0")
            )
           )
         )
       )
       (IF (= ELEVS NIL) (SETQ ELEVS "1"))
       (IF (= CODES NIL) (SETQ CODES "X"))
       (IF (= PUNTOS NIL) (SETQ PUNTOS "N"))
       (IF (/= VER1 NIL)
         (progn 
           (write-line puntos F2)
           (write-line (strcat puntos "," (rtos (car (cdr ver1)) 2 3) "," (rtos (car ver1) 2 3) "," CODES) F1)
         )
       )
    )
    )
   )
   (if (= (strcase opbus) "N")
    (PROGN
    (setq f 0)
    (SETQ VER1 "")
    (while ver1
       (setq f (1+ f))
       (SETQ VER1 (verticeSURF lin f)) 
    )
    (setq f (1- f))
    (SETQ f1 (OPEN arcdes "w"))
    (setq J 0)
    (setq elevs "1")
    (setq CODEs "V")
    (REPEAT F
       (setq J (1+ J))
       (PRINT J)
       (SETQ VER1 (verticeSURF lin J))
       (IF (/= VER1 NIL)
         (progn 
           (write-line (ITOA J) F2)
           (write-line (strcat (rtos (car ver1) 2 3) "," (rtos (car (cdr ver1)) 2 3) "," ELEVS "," (ITOA J) "," CODES) F1)
         )
       )
    )
    )
   )
  (write-line "FIN" F2)
  (write-line "" F2)
  (CLOSE F2)
   )
  )
  (CLOSE F1)
)

(DEFUN MPUN (POLI)
  (SETQ PROV 1)
  (SETQ P1T (VERTICESURF POLI PROV))
  (WHILE P1T
    (setq gpoLP (ssget "C" (suma p1T 0.10 0.10) (suma p1T -0.10 -0.10)))
    (SETQ R (sslength gpoLP))
    (SETQ PROV2 0)
    (setq mdist 100)
    (SETQ OBCOR NIL)
    (REPEAT R
      (SETQ OBJP (ssname gpoLP PROV2))
      (if (= "PUNTO" (cdr (assoc 2 (entget OBJP))))
       (progn
        (SETQ PVT (cdr (assoc 10 (entget OBJP))))
        (setq pdist (distance p1T pvT))
        (if (> mdist pdist)
         (progn
          (setq mdist pdist)
          (setq obcor objP)
         )
        )
       )
      )
      (SETQ PROV2 (1+ PROV2))
    )
    (if (AND (< 0 MDIST) (/= obcor nil))
      (PROGN
;       (ALERT "HAY UN BLOCK FUERA DE SU POSICION")
       (SETQ XYZ (cdr (assoc 10 (ENTGET OBCOR))))
       (COMMAND "ZOOM" "C" XYZ "4")
       (COMMAND "CIRCLE" XYZ ".1")
       (SETQ PROVE (ENTLAST))
       (setQ OPT (GETSTRING "DESEAS MOVERLO HACIA LA LINEA (S/N) <S> :"))
       (IF (= "CIRCLE" (cdr (assoc 0 (ENTGET PROVE))))
         (COMMAND "ERASE" PROVE "")
       )
       (IF (= OPT "")
          (SETQ OPT "S") 
       )
       (IF (= OPT "S")
        (PROGN
         (command "MOVE" OBCOR "" (cdr (assoc 10 (entget OBCOR))) P1T)
        )
       )
       (COMMAND "ZOOM" "P")
      )
    )
    (SETQ PROV (1+ PROV))
    (SETQ P1T (VERTICESURF POLI PROV))
  )         
)

(DEFUN SUMA (P VX VY)
  (SETQ X (CAR P))
  (SETQ Y (CAR (CDR P)))
  (LIST (+ X VX) (+ Y VY) (LAST P))
)

(DEFUN BUSATR (E ATR)
 (SETQ E (ENTNEXT E))
 (SETQ R 0)
 (SETQ ValAT NIL)
 (WHILE (= "ATTRIB" (cdr (assoc 0 (entget E))))
   (if (= "ATTRIB" (cdr (assoc 0 (entget E))))
      (if (= ATR (cdr (assoc 2 (entget E))))
       (PROGN
        (setq vALAT (cdr (assoc 1 (entget E))))
       )
      )
   )
   (SETQ R (1+ R))
   (SETQ E (ENTNEXT E))
 )
 (PRINT ValAT)
)

(DEFUN EXLAYER (LAYBUS)
   (SETQ LAYPROV (tblnext "layer" T))
   (SETQ FIND "N")
   (WHILE LAYPROV
     (IF (= (cdr (assoc 2 LAYPROV)) LAYBUS)
       (PROGN
         (SETQ LAYPROV NIL)
         (SETQ FIND "S")
       )
       (SETQ LAYPROV (tblnext "layer"))
     )
   )
   (PRINT FIND)
)
