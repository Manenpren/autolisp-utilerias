(defun C:CAMt()
  (COMMAND "UNDO" "M")
  (COMMAND "VIEW" "S" "CAMCOL")
  (setq PROV (CAR (ENTSEL "SELECCIONA BLOCK")))
  (setq NOMBLO (cdr (assoc 2 (entget PROV))))
  (COMMAND "INSERT" NOMBLO "0,0" "" "" "")
  (SETQ X (ENTLAST))
  (COMMAND "EXPLODE" X "")
  (SETQ GPOA (SSGET "P"))
  (SETQ P 0)
  (WHILE (/= (cdr (assoc 0 (entget PROV))) "TEXT")
    (SETQ PROV (SSNAME GPOA P))
    (SETQ P (1+ P))
  )
  (setq XY (cdr (assoc 10 (entget PROV))))
  (COMMAND "ZOOM" "C" XY "40")
  (SETQ P 0)
  (WHILE (/= prov nil)
   (setq XY (cdr (assoc 10 (entget PROV))))
   (IF (= (cdr (assoc 0 (entget PROV))) "TEXT")
      (IF (= (cdr (assoc 8 (entget PROV))) "RETICULA")
       (COMMAND "SCALE" PROV "" XY "2")
      )
    )
    (SETQ PROV (SSNAME GPOA P))
    (SETQ P (1+ P))
  )
  (setq gpom (ssget))
  (command "move" gpom "" "0,0" "-2,0")
  (setq gpom (ssget))
  (command "move" gpom "" "0,0" "0,-.32")
   (COMMAND "BLOCK" NOMBLO "Y" "0,0" GPOA "")
   (COMMAND "VIEW" "R" "CAMCOL")
)
