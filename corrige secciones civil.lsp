(defun c:CORRIGECV ()
  (COMMAND "UNDO" "M")
  (command "osnap" "none")
  (print "\n Seleciona los elementos a procesar ")
  (setq gpo (ssget '((8 . "CVL_SECC_CUAD"))))
  (SETQ P2 0)  
  (SETQ PROV (SSNAME GPO P2))
  (SETQ AO (ENTGET PROV))
  (WHILE (/= PROV NIL)
    (SETQ xyz (cdr (assoc 10 AO)))
    (SETQ xyz2 (cdr (assoc 11 AO)))
    (setq punver1 (suma xyz -0.01 -0.01))
    (setq punver2 (suma xyz 0.01 0.01))
    (command "ZOOM" "W" punver1 punver2)
    (setq ss1 (ssget "C" punver1 punver2 '((8 . "CVL_SECC_CUAD"))))
    (setq punver1 (suma xyz2 -0.01 -0.01))
    (setq punver2 (suma xyz2 0.01 0.01))
    (command "ZOOM" "W" punver1 punver2)
    (setq ss2 (ssget "C" punver1 punver2 '((8 . "CVL_SECC_CUAD"))))
    (ssdel PROV ss1)
    (ssdel PROV ss2)
    (SETQ xyz (cdr (assoc 10 AO)))
    (SETQ xyz2 (cdr (assoc 11 AO)))
    (SETQ Xp1 (CAR xyz))
    (SETQ Yp1 (CADR xyz))
    (SETQ Xp2 (CAR xyz2))
    (SETQ Yp2 (CADR xyz2))
    (setq xminp xp1)
    (setq yminp yp1)
    (setq xmaxp xp1)
    (setq ymaxp yp1)
    (maximos xp1 yp1)
    (maximos xp2 yp2)
    (SETQ xyz (cdr (assoc 10 (entget (SSNAME ss1 0)))))
    (SETQ xyz2 (cdr (assoc 11 (entget (SSNAME ss1 0)))))
    (SETQ Xp1 (CAR xyz))
    (SETQ Yp1 (CADR xyz))
    (SETQ Xp2 (CAR xyz2))
    (SETQ Yp2 (CADR xyz2))
    (maximos xp1 yp1)
    (maximos xp2 yp2)
    (SETQ xyz (cdr (assoc 10 (entget (SSNAME ss2 0)))))
    (SETQ xyz2 (cdr (assoc 11 (entget (SSNAME ss2 0)))))
    (SETQ Xp1 (CAR xyz))
    (SETQ Yp1 (CADR xyz))
    (SETQ Xp2 (CAR xyz2))
    (SETQ Yp2 (CADR xyz2))
    (maximos xp1 yp1)
    (maximos xp2 yp2)
    (command "ZOOM" "W" (suma (list xmaxp ymaxp) 1 1) (suma (list xminp yminp) -1 -1))
    (setq ssdl (ssget "C" (list xmaxp ymaxp) (list xminp yminp) '((8 . "CVL_SECC_CUAD"))))
    (setq contx 0)
    (repeat 4
      (SETQ entx (SSNAME ssdl contx))
      (ssdel entx gpo)
      (setq contx (1+ contx))
    )
    (createxto)
    (SETQ PROV (SSNAME GPO P2))
    (IF (/= PROV NIL)
       (SETQ AO (ENTGET PROV))
    )
  )
)

(defun maximos (xpx ypx)
    (if (> xpx xmaxp) (setq xmaxp xpx))
    (if (< xpx xminp) (setq xminp xpx))
    (if (> ypx ymaxp) (setq ymaxp ypx))
    (if (< ypx yminp) (setq yminp ypx))
)

(defun createxto ()
  (setq ssec (ssget "C" (suma (list xmaxp ymaxp) 1 1) (suma (list xminp yminp) -1 -1)))
  (setq sspr (ssget "C" (list xmaxp ymaxp) (list xminp yminp) '((8 . "CVL_SECP"))))
  (setq sstxt (ssget "C" (suma (list xmaxp ymaxp) 1 1) (suma (list xminp yminp) -1 -1) '((8 . "CVL_SECC_TX"))))
  (setq sscl (ssget "C" (list xmaxp ymaxp) (list xminp yminp) '((8 . "CVL_LIN_CL"))))
  (SETQ P2c 0)  
  (SETQ PROVc (SSNAME sstxt P2c))
  (SETQ AOc (ENTGET PROVc))
  (WHILE (/= PROVc NIL)
    (SETQ xyzx (cdr (assoc 10 AOc)))
    (SETQ Xpc (CAR xyzx))
    (setq p2c (1+ p2c))
    (SETQ PROVc (SSNAME sstxt P2c))
    (if (< xpc xminp) (setq provc nil))
    (IF (/= PROVc NIL)
       (SETQ AOc (ENTGET PROVc))
    )
  )
  (setq elev (cdr (assoc 1 (ENTGET (SSNAME sstxt P2c)))))
  (setq elevf (CADR (cdr (assoc 10 (ENTGET (SSNAME sstxt P2c))))))
  (setq elevf (+ elevf 0.10))
  (setq contr 1)
  (setq elevcr "")
  (repeat (strlen elev)
    (setq carx (substr elev contr 1))
    (if (/= "," carx) (setq elevcr (strcat elevcr carx)))
    (setq contr (1+ contr))
  )

  (setq xl1 (CAR (cdr (assoc 10 (ENTGET (SSNAME sscl 0))))))
  (setq ejec xl1)
;  (setq xl2 (CAR (cdr (assoc 10 (ENTGET (SSNAME sscl 1))))))
;  (setq xl3 (CAR (cdr (assoc 10 (ENTGET (SSNAME sscl 2))))))
;  (if (and (< xl1 xl2) (< xl2 xl3)) (setq lcf 2))
;  (if (and (< xl3 xl2) (< xl2 xl1)) (setq lcf 2))
;  (if (and (< xl2 xl1) (< xl1 xl3)) (setq lcf 1))
;  (if (and (< xl3 xl1) (< xl1 xl2)) (setq lcf 1))
;  (if (and (< xl1 xl3) (< xl3 xl2)) (setq lcf 3))
;  (if (and (< xl2 xl3) (< xl3 xl1)) (setq lcf 3))
;  (if (= lcf 1) (PROGN (ssdel (SSNAME sscl 0) sscl) (setq ejec xl1)))
;  (if (= lcf 2) (PROGN (ssdel (SSNAME sscl 1) sscl) (setq ejec xl2)))
;  (if (= lcf 3) (PROGN (ssdel (SSNAME sscl 2) sscl) (setq ejec xl3)))
;  (COMMAND "ERASE" sscl "")
 
  (setq gpoo (ssadd))
  (SETQ P2c 0)  
  (SETQ PROVc (SSNAME sstxt P2c))
  (SETQ AOc (ENTGET PROVc))
  (WHILE (/= PROVc NIL)
    (SETQ xyzx (cdr (assoc 10 AOc)))
    (SETQ Xpc (CAR xyzx))
    (setq p2c (1+ p2c))
    (if (> (ABS (- xpc EJEC)) 1) 
      (PROGN
        (SETQ CADENAP (SUBSTR (cdr (assoc 1 AOc)) 1 4))
        (SETQ CADENAP2 (SUBSTR (cdr (assoc 1 AOc)) 1 2))
        (IF (OR (= CADENAP "OFF=") (= CADENAP2 "R=")) 
          (setq gpoo (ssadd PROVc gpoo))
        )
      )
    )
    (SETQ PROVc (SSNAME sstxt P2c))
    (IF (/= PROVc NIL)
       (SETQ AOc (ENTGET PROVc))
    )
  )
  (COMMAND "ERASE" GPOO "")
  
  (SETQ plinepr (SSNAME sspr 0))
  (setq contpl 1)
  (setq verticepl (vertice plinepr contpl))
  (SETQ Xpl (CAR verticepl))
  (SETQ Ypl (CADR verticepl))
  (if (= xpl ejec) (setq elevapr (+ (atof elevcr) (- ypl elevf))))
  (while (and (/= verticepl nil) (/= xpl ejec))
    (setq contpl (1+ contpl))
    (SETQ Xpl (CAR verticepl))
    (SETQ Ypl (CADR verticepl))
    (if (= xpl ejec) (setq elevapr (+ (atof elevcr) (- ypl elevf))))
    (setq verticepl (vertice plinepr contpl))
  )
  (setq verticea1 (vertice plinepr (- contpl 2)))
  (SETQ Xpl1 (CAR verticea1))
  (SETQ Ypl1 (CADR verticea1))
  (setq verticea2 (vertice plinepr contpl))
  (SETQ Xpl2 (CAR verticea2))
  (SETQ Ypl2 (CADR verticea2))
  (command "line" verticea1 (suma verticea1 0 3) "")
  (command "line" verticea2 (suma verticea2 0 3) "")
  (setq desnivel (strcat "ELEV =" (rtos (- elevapr (- ypl ypl1) ) 2 3)))
  (SETQ NIVEL (LIST (CAR verticea1) (+ (CADR verticea1) 1.5) 0))         
  (SETQ XYZX (CONS 10 nivel))
  (SETQ XYZX2 (CONS 11 nivel))
  (setq tamanot (cons 40 0.2))
  (setq layert (cons 8 "CVL_SECC_TX"))                            
  (SETQ TEXTX (CONS 1 Desnivel))
  (ENTMAKE (LIST '(0 . "TEXT") '(100 . "AcDbEntity") layert '(100 . "AcDbText") XYZX tamanot TEXTX '(50 . 1.5708) '(7 . "MONOTXT4") '(72 . 1) xyzx2 '(73 . 3)))
  (setq desnivel (strcat "ELEV =" (rtos (- elevapr (- ypl ypl2) ) 2 3)))
  (SETQ NIVEL (LIST (CAR verticea2) (+ (CADR verticea2) 1.5) 0))         
  (SETQ XYZX (CONS 10 nivel))
  (SETQ XYZX2 (CONS 11 nivel))
  (setq tamanot (cons 40 0.2))
  (setq layert (cons 8 "CVL_SECC_TX"))                            
  (SETQ TEXTX (CONS 1 Desnivel))
  (ENTMAKE (LIST '(0 . "TEXT") '(100 . "AcDbEntity") layert '(100 . "AcDbText") XYZX tamanot TEXTX '(50 . 1.5708) '(7 . "MONOTXT4") '(72 . 1) xyzx2 '(73 . 3)))
  (setq desnivel (strcat "DIST =" (rtos  (- Xpl1 EJEC) 2 3)))
  (SETQ NIVEL (LIST (CAR verticea1) (+ (CADR verticea1) 1.5) 0))         
  (SETQ XYZX (CONS 10 nivel))
  (SETQ XYZX2 (CONS 11 nivel))
  (setq tamanot (cons 40 0.2))
  (setq layert (cons 8 "CVL_SECC_TX"))                            
  (SETQ TEXTX (CONS 1 Desnivel))
  (ENTMAKE (LIST '(0 . "TEXT") '(100 . "AcDbEntity") layert '(100 . "AcDbText") XYZX tamanot TEXTX '(50 . 1.5708) '(7 . "MONOTXT4") '(72 . 1) xyzx2 '(73 . 1)))
  (setq desnivel (strcat "DIST =" (rtos  (- Xpl2 EJEC) 2 3)))
  (SETQ NIVEL (LIST (CAR verticea2) (+ (CADR verticea2) 1.5) 0))         
  (SETQ XYZX (CONS 10 nivel))
  (SETQ XYZX2 (CONS 11 nivel))
  (setq tamanot (cons 40 0.2))
  (setq layert (cons 8 "CVL_SECC_TX"))                            
  (SETQ TEXTX (CONS 1 Desnivel))
  (ENTMAKE (LIST '(0 . "TEXT") '(100 . "AcDbEntity") layert '(100 . "AcDbText") XYZX tamanot TEXTX '(50 . 1.5708) '(7 . "MONOTXT4") '(72 . 1) xyzx2 '(73 . 1)))
)

(defun SUMA (punto xx yy)
  (setq x (car punto))
  (setq y (car (cdr punto)))
  (setq xxx (+ x xx))
  (setq yyy (+ y yy))
  (list xxx yyy)
)

(defun vertice (poli nov)
  (setq listap (entget poli))
  (setq nver 0)
  (setq salir "N")
  (while (= salir "N")
    (setq sublisp (car listap))
    (if (= 10 (car sublisp))
      (progn
        (setq punto (cdr sublisp))  
        (setq nver (+ nver 1))
      )
    )
    (setq listap (cdr listap))
    (if listap
      (setq salir "N")
      (setq salir "S")
    )
    (if (= nov nver)
      (setq salir "S")
    )
  )
  (if (not listap)
    (setq punto nil)
  )
  (setq punto punto)
)
