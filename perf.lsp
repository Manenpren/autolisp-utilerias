(defun SUMA (punto xx yy)
  (setq x (car punto))
  (setq y (car (cdr punto)))
  (setq xxx (+ x xx))
  (setq yyy (+ y yy))
  (list xxx yyy)
)

(defun DatC (linea nudato)
  (setq cuen 0)
  (setq cuecom 0)
  (setq salir "N")
  (setq cadena "")
  (while (/= salir "S")
    (setq cuen (+ cuen 1))
    (setq caracter (substr linea cuen 1))
    (if (= caracter ",")
      (setq cuecom (+ cuecom 1))
    )
    (if (= cuecom (- nudato 1))
      (if (/= caracter ",")
        (setq cadena (strcat cadena caracter))
      )
    )
    (if (or (= cuecom nudato) (>= cuen (strlen linea)))
      (setq salir "S")
    )
  )
  (setq cadena cadena)
)

(defun entero (numed)
  (setq numed (rtos numed 2 8))
  (setq cuecar 1)
  (setq letra "")
  (while (/= letra ".")
    (setq letra (substr numed cuecar 1))
    (setq cuecar (+ cuecar 1))
    (if (= letra "")
      (setq letra ".")
    )
  )
  (setq frac (atof (substr numed 1 (- cuecar 1))))
)

(defun fraccion (numed)
  (setq numed (rtos numed 2 8))
  (setq cuecar 1)
  (setq letra "")
  (while (/= letra ".")
    (setq letra (substr numed cuecar 1))
    (setq cuecar (+ cuecar 1))
    (if (= letra "")
      (setq letra ".")
    )
  )
  (setq frac (atof (substr numed (- cuecar 1))))
)

(defun AMinSec (angull)
  (setq min2 (* (fraccion angull) 60))
  (setq min1 (rtos (entero (* (fraccion angull) 60)) 2 0))
  (setq sec (rtos (* (fraccion min2) 60) 2 0))
  (if (> 0 angull)
    (setq angull (* angull -1))
  )
  (setq angres (strcat (rtos (entero angull) 2 0) "%%d" min1 "'" sec "''"))
)


(defun cottop (NUMERO)
  (if (> numero 0)
   (progn
      (setq nombre (rtos numero 2 3))
      (setq nombre (rtos (/ (atof nombre) 1000) 2 7))
      (SETQ LNG (STRLEN NOMBRE))
      (SETQ NOMBLOx "")
      (SETQ CONT 0)
      (REPEAT LNG
          (SETQ CONT (1+ CONT))
          (setq CARACTER (substr NOMBRE CONT 1))
          (IF (= CARACTER ".") (SETQ CARACTER "+"))
          (setq nomblox (STRCAT NOMBLOx CARACTER))
      )
    (setq nomblox (strcat (substr nomblox 1 (- lng 4)) "." (substr nomblox (- lng 3) 3)))
    (setq lng (1+ lng))
    (if (= (substr nomblox (- lng 3) 3) "000") (setq nomblox (substr nomblox 1 (- lng 5))))
    (setq nuetex nomblox)
   )
   (setq nuetex "0+000")
  )
)

(defun vertice (poli nov)
  (setq listap (entget poli))
  (setq nver 0)
  (setq salir "N")
  (while (= salir "N")
    (setq sublisp (car listap))
    (if (= 10 (car sublisp))
      (progn
        (setq punto (cdr sublisp))  
        (setq nver (+ nver 1))
      )
    )
    (setq listap (cdr listap))
    (if listap
      (setq salir "N")
      (setq salir "S")
    )
    (if (= nov nver)
      (setq salir "S")
    )
  )
  (if (not listap)
    (setq punto nil)
  )
  (setq punto punto)
)

(defun perfIL ()
  (command "LAYER" "M" "PERFIL" "")
  (command "LAYER" "M" "RETICULA" "")
  (command "LAYER" "S" "PERFIL" "")
  (setq polper (car (entsel "Selecciona la polylinea del perfil: ")))
  (setq nomblo (strcase (getstring "Nombre del bloque a utilizar: <PUN2>")))
  (IF (= NOMBLO "")
    (SETQ NOMBLO "PUN2")
  )
  (setq nomblo (strcase nomblo))
  (setq exagera (getreal "Exageración vertical: <10> "))
  (IF (= EXAGERA NIL)
    (SETQ EXAGERA 10)
  )
  (MPUN POLPER)
  (setq cuenta 1)
  (setq vez 0)
  (setq dis 0)
  (setq disac 0)
  (command "VIEW" "S" "HOLA")
  (setq elevma -10000)
  (setq elevme 999999)
  (while (vertice polper cuenta)
    (setq PunverA PunVer)
    (setq punver (vertice polper cuenta))
    (setq punver1 (suma punver -0.01 -0.01))
    (setq punver2 (suma punver 0.01 0.01))
    (command "ZOOM" "W" punver1 punver2)
    (setq GpoPun (ssget "C" punver1 punver2))
    (setq ElevA Elev)
    (setq DisA DisAc)
    (setq cuenta2 0)
    (setq elev nil)
    (while (= elev nil)
      (setq nomobj (ssname gpopun cuenta2))
;      (IF (= NOMOBJ NIL) (PROGN (ALERT "NO SE ENCONTRO BLOCK CON ATRIBUTO DE ELEVACION") (EXIT)))
      (SETQ PV (cdr (assoc 10 (entget nomobj))))
      (SETQ XV (CAR PV))
      (SETQ YV (CADR PV))
      (SETQ X1 (CAR PUNVER))
      (SETQ Y1 (CADR PUNVER))
      (if (= "INSERT" (cdr (assoc 0 (entget nomobj))))
       (progn
        (if (= (STRCASE (cdr (assoc 2 (entget nomobj)))) nomblo)
         (IF (AND (= (RTOS XV 2 2) (RTOS X1 2 2)) (= (RTOS YV 2 2) (RTOS Y1 2 2)))
          (progn
            (SETQ ELEV NIL)
            (setq elev (BUSATR NOMOBJ "ELEV"))
            (IF (= ELEV NIL)
              (setq elev (BUSATR NOMOBJ "ELEVACION"))
            )
            (setq identifi (BUSATR NOMOBJ "PUNTO"))
          )
         )
        )
       )
      )
      (setq cuenta2 (+ cuenta2 1))
    )
    (setq cuenta (+ cuenta 1))
    (setq vez 1)
    (if (/= (type elev) "REAL")
     (PROGN
      (if (> (atof elev) elevma)
        (setq elevma (atof elev)) 
      )
      (if (< (atof elev) elevme)
        (setq elevme (atof elev)) 
      )
     )
     (PROGN
      (if (> elev elevma)
        (setq elevma (atof elev)) 
      )
      (if (< elev elevme)
        (setq elevme (atof elev)) 
      )
     )
    )
  )
  (setq cuenta 1)
  (setq vez 0)
  (setq dis 0)
  (setq disac 0)
  (command "VIEW" "S" "HOLA")
  (SETQ PEGPO (SSADD))
  (while (vertice polper cuenta)
    (setq PunverA PunVer)
    (setq punver (vertice polper cuenta))
    (setq punver1 (suma punver -0.01 -0.01))
    (setq punver2 (suma punver 0.01 0.01))
    (command "ZOOM" "W" punver1 punver2)
    (setq GpoPun (ssget "C" punver1 punver2))
    (setq ElevA Elev)
    (setq DisA DisAc)
    (setq cuenta2 0)
    (while (/= cuenta2 (sslength GpoPun))
      (setq nomobj (ssname gpopun cuenta2))
      (SETQ PV (cdr (assoc 10 (entget nomobj))))
      (SETQ XV (CAR PV))
      (SETQ YV (CADR PV))
      (SETQ X1 (CAR PUNVER))
      (SETQ Y1 (CADR PUNVER))
      (if (= "INSERT" (cdr (assoc 0 (entget nomobj))))
      (progn
      (if (= (STRCASE (cdr (assoc 2 (entget nomobj)))) nomblo)
       (IF (AND (= (RTOS XV 2 2) (RTOS X1 2 2)) (= (RTOS YV 2 2) (RTOS Y1 2 2)))
        (progn
          (SETQ ELEV NIL)
          (setq elev (BUSATR NOMOBJ "ELEV"))
          (IF (= ELEV NIL)
            (setq elev (BUSATR NOMOBJ "ELEVACION"))
          )
          (setq identifi (BUSATR NOMOBJ "PUNTO"))
        )
       )
      )
      )
      )
      (setq cuenta2 (+ cuenta2 1))
    )
    (if (= vez 0)
      (progn
        (setq TEXTOPER (rtos 0 2 3))
        (setq texto1 "0+000.000")
      )
    )
    (if (/= vez 0)
      (progn
        (setq dis (distance PunVerA PunVer))
        (setq disac (+ disac dis))
        (setq PunPer1 (list disA (* (atof elevA) exagera)))
        (setq PunPer2 (list disac (* (atof elev) exagera)))
        (command "PLINE" PunPer1 PunPer2 "")
        (SETQ PROV (ENTLAST))
        (SSADD PROV PEGPO)
      )
    )
    (setq cuenta (+ cuenta 1))
    (setq vez 1)
  )
  (SETQ EXAV EXAGERA)
  (COMMAND "PEDIT" (SSNAME PEGPO 0) "J" PEGPO "" "W" altn "" "change" (entlast) "" "p" "c" cltn "")
  (SETQ POLPER (ENTLAST))
  (setq res (getstring " Crear reticula natural o equidistante: (N/E)"))
  (if (= (strcase res) "N")
    (CreaRet)
    (CreaRet2)
  )
)

(defun verticebd (poli)
  (setq listap (entget poli))
  (setq nver 0)
  (setq salir "N")
  (SETQ matrizpol NIL)
  (while (= salir "N")
    (setq sublisp (car listap))
    (if (= 10 (car sublisp))
      (progn
        (setq punto (cdr sublisp))  
        (setq CONCATENADO (cons nver punto))        
        (setq matrizpol (append matrizpol (list CONCATENADO)))
        (setq nver (+ nver 1))
      )
    )
    (setq listap (cdr listap))
    (if listap
      (setq salir "N")
      (setq salir "S")
    )
  )
  (setq matrizpol matrizpol)
)

(defun CreaRet2 ()
  (if (not PolPer)
    (setq PolPer (car (entsel "Polylinea para crear el perfil: ")))
  )
  (if (not ExaV)
    (progn
      (if (= opcprog "1")  
        (setq ExaV (getint " Exageracion vertical: <10> "))
        (setq ExaV (atoi defy))
      )
      (IF (= EXAV NIL)
        (SETQ EXAV 10)
      )
    )
  )
  (setq vertices (verticebd polper))
  (setq verpol (cdr (assoc 0 vertices)))
  (setq cuever 1)
  (setq EMax (car (cdr verpol)))
  (setq EMin EMax)
  (setq CMin (car verpol))
  (while verpol
    (setq xpol (car verpol))
    (setq ypol (car (cdr verpol)))
    (if (> ypol EMax)
      (setq EMax ypol)
    )
    (if (< ypol EMin)
      (setq EMin ypol)
    )
    (setq CMax (car verpol))
    (setq verpol (cdr (assoc cuever vertices)))
    (setq cuever (+ cuever 1))
  )
  (setq emin (/ emin exav))
  (setq emax (/ emax exav))
  (write-line (strcat "Elevacion minima detectada: " (rtos Emin 2 2)))
  (write-line (strcat "Elevacion maxima detectada: " (rtos Emax 2 2)))
  (if (= opcprog "1")
    (progn
      (setq SepReth (getreal "Separacion de las elevaciones en reticula: "))
      (setq SepElev (getreal "Separacion de los cadenamientos en reticula: "))
    )
    (progn
      (setq SepReth (atof sepelev2))
      (setq SepElev (atof sepcad))
    )
  )
;  (SETQ EMIN (FIX EMIN)) 
  (SETQ EMIN (FIX (/ EMIN sepreth))) 
  (SETQ EMIN (* EMIN sepreth))
  (SETQ CALC (FIX (/ (- EMAX EMIN ) sepreth)))
  (SETQ CALC (1+ CALC))
  (SETQ EMAX (+ (* CALC SEPreth) EMIN))
  (write-line (strcat "Elevacion minima detectada: " (rtos Emin 2 2)))
  (write-line (strcat "Elevacion maxima detectada: " (rtos Emax 2 2)))
  (command "LAYER" "M" "RETICULA" "S" "RETICULA" "")
  (setq emin (* emin exav))
  (setq emax (* emax exav))
  (setq p1 (list cmin emin))
  (setq p2 (list cmax emin))
  (setq p3 (list cmin emax))
  (setq p4 (list cmax emax))
  (setq px (list cmin (- emin 100)))
  (command "zoom" "w" p4 px "")
  (setq pX1X (list 10 cmin emin 0))
  (setq pX2Y (list 11 cmax emin 0))
  (setq pX2X (list 10 cmax emin 0))
  (setq pX3X (list 10 cmin emax 0))
  (setq pX3Y (list 11 cmin emax 0))
  (setq pX4 (list 11 cmax emax 0))
  (setq colorl (cons 62  (atoi clenv)))
  (ENTMAKE (LIST '(0 . "LINE") '(100 . "AcDbEntity") '(8 . "0") '(100 . "AcDbLine") PX1X PX2Y colorl))
;  (command "LINE" p1 p2 "")
;  (command "change" "L" "" "P" "C" "3" "")
  (ENTMAKE (LIST '(0 . "LINE") '(100 . "AcDbEntity") '(8 . "0") '(100 . "AcDbLine") PX3X PX4 colorl))
;  (command "LINE" p3 p4 "")
;  (command "change" "L" "" "P" "C" "3" "")
  (ENTMAKE (LIST '(0 . "LINE") '(100 . "AcDbEntity") '(8 . "0") '(100 . "AcDbLine") PX1X PX3Y colorl))
;  (command "LINE" p1 p3 "")
;  (command "change" "L" "" "P" "C" "3" "")
  (ENTMAKE (LIST '(0 . "LINE") '(100 . "AcDbEntity") '(8 . "0") '(100 . "AcDbLine") PX2X PX4 colorl))
;  (command "LINE" p2 p4 "")
;  (command "change" "L" "" "P" "C" "3" "")
  (setq SepRetH (* SepRetH ExaV))
  (setq CueLin 1)
  (setq EleRet EMin)
  (while (> (+ EMax SepRetH) EleRet)
    (setq PunRet (list (- CMin 2) EleRet))
    (setq PunRet2 (list CMax EleRet))
    (setq PunRetX (list 10 (- CMin 2) EleRet 0))
    (setq PunRetX2 (list 11 CMax EleRet 0))
;    (command "INSERT" (strcat RUTA "BLOCKS\\TEXTOPER") (suma PunRet -20 0) "3" "3" "0" "" "")
;    (SETQ ENTP(ENTLAST))
;    (SETQ ENTP(ENTNEXT ENTP))
    (setq valor (rtos (/ EleRet ExaV) 2 2))
    (SETQ LNG (STRLEN valor))
    (setq lng (1+ lng))
    (if (= (substr valor (- lng 2) 2) "00") (setq valor (substr valor 1 (- lng 4))))
    (SETQ XYZX (CONS 10 (suma PunRet -20 0)))
    (SETQ TEXTX (CONS 1 VALOR))
    (setq colorcot (cons 62  (atoi ctcot)))
    (setq tamanot (cons 40 (atoi ttcot)))           
    (ENTMAKE (LIST '(0 . "TEXT") '(100 . "AcDbEntity") '(8 . "0") '(100 . "AcDbText") XYZX tamanot TEXTX colorcot))
;    (COMMAND "ATTEDIT" "" "" "" "" ENTP "V" "R" valor "")
    (if (= tlret "2") (setq valorx "HIDDEN") (setq valorx "Bylayer"))
    (setq colorl (cons 62  (atoi clret)))
    (setq valorx (cons 6  valorx))
    (ENTMAKE (LIST '(0 . "LINE") '(100 . "AcDbEntity") '(8 . "0") valorx '(100 . "AcDbLine") PUNRETX PUNRETX2 colorl))
;    (command "LINE" PunRet PunRet2 "")
    (command "CHANGE" (ENTLAST) "" "P" "LT" "HIDDEN" "")
    (setq EleRet (+ EleRet SepRetH))
    (setq CueLin (+ CueLin 1))
  )
  (setq verpol (cdr (assoc 1 vertices)))
  (setq cuever 1)
  (setq CAnt 0)
  (setq CadV 0)
  (setq NoVerA -1)
  (setq Sigue "SI")
  (setq cuever 0)
  (while Sigue
    (setq PunRet (list CadV (- EMin 2)))
    (setq verpol (cdr (assoc 1 vertices)))
    (while verpol
      (setq cuever (+ cuever 1))
      (setq verpol (cdr (assoc cuever vertices)))
      (if (not verpol)
        (progn
          (setq sigue nil)
          (setq CadT (car (cdr (assoc (- cuever 1) vertices))))
        )
      )
      (setq CadVA (car verpol))
      (if (> CadVA CadV)
        (progn
          (setq NoVerA cuever)
          (setq verpol nil)
        )
      )
    )
    (if sigue
      (progn
        (setq nover1 (cdr (assoc (- NoVerA 1) vertices)))
        (setq nover2 (cdr (assoc NoVerA vertices)))
        (setq PunVerA (inters NoVer1 NoVer2 (list CadV (- (car (cdr NoVer1)) 1000)) (list CadV (+ (car (cdr NoVer1)) 1000)) ))
        (SETQ PUNVERAX (APPEND '(10) PUNVERA '(0)))
        (setq CadV (+ CadV SepEleV))
        (setq PunRet2 (list (car PunVerA) (- Emin 45)))
        (setq PunRet (list (car PunVerA) (- EMin 2)))
        (setq PunRetX (list 11 (car PunVerA) (- EMin 2) 0))
;        (command "LINE" PunVerA PunRet "")
        (ENTMAKE (LIST '(0 . "LINE") '(100 . "AcDbEntity") '(8 . "0") valorx '(100 . "AcDbLine") PUNVERAX PUNRETX colorl))
;        (command "INSERT" (strcat RUTA "BLOCKS\\TEXTOPER") (suma PunRet2 0 -30) "3" "3" "90" "" "")
;        (SETQ ENTP(ENTLAST))
;        (SETQ ENTP(ENTNEXT ENTP))
        (SETQ XYZX (CONS 10 (suma PunRet 0 (- (* 14 (atof ttest))))))
        (SETQ TEXTX (CONS 1 (cottop (car PunVerA))))
        (setq colort (cons 62  (atoi ctcad)))
        (setq tamanot (cons 40 (atoi ttcad)))           
        (ENTMAKE (LIST '(0 . "TEXT") '(100 . "AcDbEntity") '(8 . "0") '(100 . "AcDbText") XYZX tamanot TEXTX '(50 . 1.5708) colort))
;        (COMMAND "ATTEDIT" "" "" "" "" ENTP "V" "R" (cottop (car PunVerA)) "")
        (setq ERt (rtos (/ (car (cdr PunVerA)) ExaV) 2 2))
        (setq CPar (rtos (- (car PunVerA) CAnt) 2 2))
;        (command "INSERT" (strcat RUTA "BLOCKS\\TEXTOPER") (suma PunRet 0 -20) "3" "3" "90" "" "")
;        (SETQ ENTP(ENTLAST))
;        (SETQ ENTP(ENTNEXT ENTP))
;        (COMMAND "attedit" "" "" "" "" entp "v" "R" ERt "")
        (SETQ XYZX (CONS 10 (suma PunRet 0 (- (* 6 (atof ttest))))))
        (SETQ TEXTX (CONS 1 ERT))
        (setq colort (cons 62  (atoi ctest)))
        (setq tamanot (cons 40 (atoi ttest)))           
        (ENTMAKE (LIST '(0 . "TEXT") '(100 . "AcDbEntity") '(8 . "0") '(100 . "AcDbText") XYZX tamanot TEXTX '(50 . 1.5708) colort))
        (setq cuever (- cuever 1))
      )
    )
  )


  (setq CadV CadT)
  (setq PunRet (list CadV (- EMin 2)))
  (setq cuever 0)
  (setq verpol (cdr (assoc 1 vertices)))
  (while verpol
    (setq cuever (+ cuever 1))
    (setq verpol (cdr (assoc cuever vertices)))
    (if (not verpol)
      (progn
        (setq sigue nil)
        (setq CadT (car (cdr (assoc (- cuever 1) vertices))))
      )
    )
    (setq CadVA (car verpol))
    (if (>= CadVA CadV)
      (progn
        (setq NoVerA cuever)
        (setq verpol nil)
      )
    )
  )
  (setq nover1 (cdr (assoc (- NoVerA 1) vertices)))
  (setq nover2 (cdr (assoc NoVerA vertices)))
  (setq PunVerA (inters NoVer1 NoVer2 (list CadV (- (car (cdr NoVer1)) 1000)) (list CadV (+ (car (cdr NoVer1)) 1000)) ))
  (setq CadV (+ CadV SepEleV))
  (setq PunRet2 (list (car PunVerA) (- Emin 45)))
  (setq PunRet (list (car PunVerA) (- EMin 2)))
;  (command "LINE" PunVerA PunRet "")
  (setq pX1X (list 10 (car PunVerA) (caDr PunVerA) 0))
  (setq pX2Y (list 11 (car PunrET) (caDr PunrET) 0))
  (setq colorl (cons 62  (atoi clenv)))
  (ENTMAKE (LIST '(0 . "LINE") '(100 . "AcDbEntity") '(8 . "0") '(100 . "AcDbLine") PX1X PX2Y colorl))
;  (command "INSERT" (strcat RUTA "BLOCKS\\TEXTOPER") (suma PunRet2 0 -30) "3" "3" "90" "" "")
;  (SETQ ENTP(ENTLAST))
;  (SETQ ENTP(ENTNEXT ENTP))
;  (COMMAND "attedit" "" "" "" "" entp "v" "R" (cottop (car PunVerA)) "")
  (SETQ XYZX (CONS 10 (suma PunRet 0 (- (* 14 (atof ttest))))))
  (SETQ TEXTX (CONS 1 (cottop (car PunVerA))))
  (setq colort (cons 62  (atoi ctcad)))
  (setq tamanot (cons 40 (atoi ttcad)))           
  (ENTMAKE (LIST '(0 . "TEXT") '(100 . "AcDbEntity") '(8 . "0") '(100 . "AcDbText") XYZX tamanot TEXTX '(50 . 1.5708) colort))
  (setq ERt (rtos (/ (car (cdr PunVerA)) ExaV) 2 2))
  (setq CPar (rtos (- (car PunVerA) CAnt) 2 2))
;  (command "INSERT" (strcat RUTA "BLOCKS\\TEXTOPER") (suma PunRet 0 -20) "3" "3" "90" "" "")
;  (SETQ ENTP(ENTLAST))
;  (SETQ ENTP(ENTNEXT ENTP))
;  (COMMAND "attedit" "" "" "" "" entp "v" "R" ERt "")
  (SETQ XYZX (CONS 10 (suma PunRet 0 (- (* 6 (atof ttest))))))
  (SETQ TEXTX (CONS 1 ERT))
  (setq colort (cons 62  (atoi ctest)))
  (setq tamanot (cons 40 (atoi ttest)))           
  (ENTMAKE (LIST '(0 . "TEXT") '(100 . "AcDbEntity") '(8 . "0") '(100 . "AcDbText") XYZX tamanot TEXTX '(50 . 1.5708) colort))
)

(defun CreaRet ()
  (if (not PolPer)
    (setq PolPer (car (entsel "Polylinea para crear el perfil: ")))
  )
  (if (not ExaV)
    (progn
      (if (= opcprog "1")  
        (setq ExaV (getint " Exageracion vertical: <10> "))
        (setq ExaV (atoi defy))
      )
      (IF (= EXAV NIL)
        (SETQ EXAV 10)
      )
    )
  )
  (setq vertices (verticebd polper))
  (setq verpol (cdr (assoc 0 vertices)))
  (setq cuever 1)
  (setq EMax (car (cdr verpol)))
  (setq EMin EMax)
  (setq CMin (car verpol))
  (while verpol
    (setq xpol (car verpol))
    (setq ypol (car (cdr verpol)))
    (if (> ypol EMax)
      (setq EMax ypol)
    )
    (if (< ypol EMin)
      (setq EMin ypol)
    )
    (setq CMax (car verpol))
    (setq verpol (cdr (assoc cuever vertices)))
    (setq cuever (+ cuever 1))
  )
  (setq emin (/ emin exav))
  (setq emax (/ emax exav))
  (write-line (strcat "Elevacion minima detectada: " (rtos Emin 2 2)))
  (write-line (strcat "Elevacion maxima detectada: " (rtos Emax 2 2)))
  (if (= opcprog "1")
    (setq SepRetH (getreal "Separacion de las elevaciones de la reticula: "))
    (setq SepReth (atof sepelev))
  )
;  (SETQ EMIN (FIX EMIN)) 
  (SETQ EMIN (FIX (/ EMIN sepreth)))
  (SETQ EMIN (* EMIN sepreth))
  (SETQ CALC (FIX (/ (- EMAX EMIN ) sEPretH)))
  (SETQ CALC (1+ CALC))
  (SETQ EMAX (+ (* CALC SEpretH) EMIN))
  (write-line (strcat "Elevacion minima detectada: " (rtos Emin 2 2)))
  (write-line (strcat "Elevacion maxima detectada: " (rtos Emax 2 2)))
  (command "LAYER" "M" "RETICULA" "S" "RETICULA" "")
  (setq emin (* emin exav))
  (setq emax (* emax exav))
  (setq p1 (list cmin emin))
  (setq p2 (list cmax emin))
  (setq p3 (list cmin emax))
  (setq p4 (list cmax emax))
  (setq px (list cmin (- emin 100)))
  (command "zoom" "w" p4 px "")
  (setq pX1X (list 10 cmin emin 0))
  (setq pX2Y (list 11 cmax emin 0))
  (setq pX2X (list 10 cmax emin 0))
  (setq pX3X (list 10 cmin emax 0))
  (setq pX3Y (list 11 cmin emax 0))
  (setq pX4 (list 11 cmax emax 0))
  (setq colorl (cons 62  (atoi clenv)))
  (ENTMAKE (LIST '(0 . "LINE") '(100 . "AcDbEntity") '(8 . "0") '(100 . "AcDbLine") PX1X PX2Y colorl))
;  (command "LINE" p1 p2 "")
;  (command "change" "L" "" "P" "C" "3" "")
  (ENTMAKE (LIST '(0 . "LINE") '(100 . "AcDbEntity") '(8 . "0") '(100 . "AcDbLine") PX3X PX4 colorl))
;  (command "LINE" p3 p4 "")
;  (command "change" "L" "" "P" "C" "3" "")
  (ENTMAKE (LIST '(0 . "LINE") '(100 . "AcDbEntity") '(8 . "0") '(100 . "AcDbLine") PX1X PX3Y colorl))
;  (command "LINE" p1 p3 "")
;  (command "change" "L" "" "P" "C" "3" "")
  (ENTMAKE (LIST '(0 . "LINE") '(100 . "AcDbEntity") '(8 . "0") '(100 . "AcDbLine") PX2X PX4 colorl))

  (setq px (list cmin (- emin 100)))
  (command "zoom" "w" p4 px "")
  (setq SepRetH (* SepRetH ExaV))
  (setq CueLin 1)
  (setq EleRet EMin)
  (while (> (+ EMax SepRetH) EleRet)
    (setq PunRet (list (- CMin 2) EleRet))
    (setq PunRet2 (list CMax EleRet))
    (setq PunRetX (list 10 (- CMin 2) EleRet 0))
    (setq PunRetX2 (list 11 CMax EleRet 0))
    (setq valor (rtos (/ EleRet ExaV) 2 2))
    (SETQ LNG (STRLEN valor))
    (setq lng (1+ lng))
    (if (= (substr valor (- lng 2) 2) "00") (setq valor (substr valor 1 (- lng 4))))
    (SETQ XYZX (CONS 10 (suma PunRet -20 0)))
    (SETQ TEXTX (CONS 1 VALOR))
    (setq colorcot (cons 62  (atoi ctcot)))
    (setq tamanot (cons 40 (atoi ttcot)))           
    (ENTMAKE (LIST '(0 . "TEXT") '(100 . "AcDbEntity") '(8 . "0") '(100 . "AcDbText") XYZX tamanot TEXTX colorcot))
;    (COMMAND "ATTEDIT" "" "" "" "" ENTP "V" "R" valor "")
    (if (= tlret "2") (setq valorx "HIDDEN") (setq valorx "Bylayer"))
    (setq colorl (cons 62  (atoi clret)))
    (setq valorx (cons 6  valorx))
    (ENTMAKE (LIST '(0 . "LINE") '(100 . "AcDbEntity") '(8 . "0") valorx '(100 . "AcDbLine") PUNRETX PUNRETX2 colorl))
;    (command "LINE" PunRet PunRet2 "")
    (command "CHANGE" (ENTLAST) "" "P" "LT" "HIDDEN" "")
    (setq EleRet (+ EleRet SepRetH))
    (setq CueLin (+ CueLin 1))
  )
  (setq verpol (cdr (assoc 1 vertices)))
  (setq cuever 1)
  (setq CAnt 0)
  (while verpol
    (setq PunRet (list (car verpol) (- EMin 2)))
    (setq PunRet2 (list (car verpol) (- Emin 45)))
    (setq pX1X (list 10 (car VERPOL) (caDr VERPOL) 0))
    (setq pX2Y (list 11 (car PunrET) (caDr PunrET) 0))
    (setq colorl (cons 62  (atoi clRET)))
    (ENTMAKE (LIST '(0 . "LINE") '(100 . "AcDbEntity") '(8 . "0") valorx '(100 . "AcDbLine") PX1X PX2Y colorl))
;    (command "LINE" verpol PunRet "")
;    (command "INSERT" (strcat RUTA "BLOCKS\\TEXTOPER") (suma PunRet2 0 -30) "3" "3" "90" "" "")
;    (SETQ ENTP(ENTLAST))
;    (SETQ ENTP(ENTNEXT ENTP))
;    (COMMAND "ATTEDIT" "" "" "" "" ENTP "V" "R" (cottop (car verpol)) "")
    (SETQ XYZX (CONS 10 (suma PunRet 0 (- (* 17 (atof ttest))))))
    (SETQ TEXTX (CONS 1 (cottop (car verpol))))
    (setq colort (cons 62  (atoi ctcad)))
    (setq tamanot (cons 40 (atoi ttcad)))           
    (ENTMAKE (LIST '(0 . "TEXT") '(100 . "AcDbEntity") '(8 . "0") '(100 . "AcDbText") XYZX tamanot TEXTX '(50 . 1.5708) colort))
    (setq ERt (rtos (/ (car (cdr verpol)) ExaV) 2 2))
    (setq CPar (rtos (- (car verpol) CAnt) 2 2))
;    (command "INSERT" (strcat RUTA "BLOCKS\\TEXTOPER") (suma PunRet 0 -20) "3" "3" "90" "" "")
;    (SETQ ENTP(ENTLAST))
;    (SETQ ENTP(ENTNEXT ENTP))
;    (COMMAND "ATTEDIT" "" "" "" "" ENTP "V" "R" ERt "")
    (SETQ XYZX (CONS 10 (suma PunRet 0 (- (* 6 (atof ttest))))))
    (SETQ TEXTX (CONS 1 ERT))
    (setq colort (cons 62  (atoi ctest)))
    (setq tamanot (cons 40 (atoi ttest)))           
    (ENTMAKE (LIST '(0 . "TEXT") '(100 . "AcDbEntity") '(8 . "0") '(100 . "AcDbText") XYZX tamanot TEXTX '(50 . 1.5708) colort))
    (setq CAnt (car verpol))
    (setq cuever (+ cuever 1))
    (setq verpol (cdr (assoc cuever vertices)))
  )
)

(defun C:CPO ()
  (IF (= OPTPERF 0)
   (PROGN
    (setq NOMARCH (getfiled "ARCHIVO PARA CREAR POLYLINEA" "*." "CSV" 18))
    (setq ColX (getint " Columna para X: "))
    (setq ColY (getint " Columna para Y: "))
   )
   (PROGN
     (SETQ COLX 4)
     (SETQ COLY 3)
   )
  )
  (if (= opcprog "1")  
    (setq ExaV (getint " Exageracion vertical: <10> "))
    (setq ExaV (atoi defy))
  )
  (IF (= EXAV NIL)
    (SETQ EXAV 10)
  )
  (setq arch (open NomArch "r"))
  (setq lin (read-line arch))
  (setq cuenta 0)
  (setq gpop (ssadd))
  (while lin
    (setq px (atof (DatC lin ColX)))
    (setq py (atof (DatC lin ColY)))
    (setq py (* py ExaV))
    (setq pun (list px py))
    (if (= cuenta 1)
      (progn
        (command "PLINE" puna pun "")
        (ssadd (entlast) gpop)
      )
    )
    (setq lin (read-line arch))
    (setq cuenta 1)
    (setq puna pun)
  )
  (setq l (ssname gpop 0))
  (command "PEDIT" L "J" gpop "" "w" altn "" "change" (entlast) "" "p" "c" cltn "")
  (setq PolPer (entlast))
  (setq res (getstring " Crear reticula natural o equidistante: (N/E)"))
  (if (= (strcase res) "N")
    (CreaRet)
    (CreaRet2)
  )
  (SETQ OPTPERF 0)
)

(DEFUN C:PERF2 ()
  (command "undo" "m")
  (COMMAND "LUNITS" 2)
  (COMMAND "LUPREC" 7)
  (COMMAND "AUNITS" 0)
  (COMMAND "AUPREC" 4)
  (COMMAND "ANGDIR" 0)
  (COMMAND "ANGBASE" 0.0)
  (COMMAND "DIMZIN" 0)
  (setq ARCINSAT (open (strcat ruta "configuraciones de programas\\perfil.CFG") "r"))
  (IF (= ARCINSAT NIL)
   (PROGN
     (setq ttcad "3")
     (setq ftcad "")
     (setq ctcad "5")
     (setq ttcot "3")
     (setq ftcot "")
     (setq ctcot "5")
     (setq ttest "3")
     (setq ftest "")
     (setq ctest "5")
     (setq tlret "2")
     (setq alret "0")
     (setq clret "2")
     (setq tltn "1")
     (setq altn "0.1")
     (setq cltn "3")
     (setq tlenv "1")
     (setq alenv "0.2")
     (setq clenv "3")
     (setq defx "1")
     (setq defy "10")
     (setq sepelev2 "1")
     (setq sepcad "20")
     (setq opcprog "1")
   )
   (PROGN
     (setq ttcad (read-line arCINSAT))
     (setq ftcad (read-line arCINSAT))
     (setq ctcad (read-line arCINSAT))
     (setq ttcot (read-line arCINSAT))
     (setq ftcot (read-line arCINSAT))
     (setq ctcot (read-line arCINSAT))
     (setq ttest (read-line arCINSAT))
     (setq ftest (read-line arCINSAT))
     (setq ctest (read-line arCINSAT))
     (setq tlret (read-line arCINSAT))
     (setq alret (read-line arCINSAT))
     (setq clret (read-line arCINSAT))
     (setq tltn (read-line arCINSAT))
     (setq altn (read-line arCINSAT))
     (setq cltn (read-line arCINSAT))
     (setq tlenv (read-line arCINSAT))
     (setq alenv (read-line arCINSAT))
     (setq clenv (read-line arCINSAT))
     (setq defx (read-line arCINSAT))
     (setq defy (read-line arCINSAT))
     (setq sepelev2 (read-line arCINSAT))
     (setq sepcad (read-line arCINSAT))
     (setq opcprog (read-line arCINSAT))
     (CLOSE ARCINSAT)
   )
  )
  (setq dcl_id (load_dialog (strcat ruta "dialogos\\perf.dcl"))) 
  (if (not (new_dialog "perf" dcl_id))   
    (exit)                                
                                          
  )
 (setq width (dimx_tile  "arcsv")
       height (dimy_tile "arcsv"))
 (start_image "arcsv")  
 (slide_image 1 1 width height (STRCAT RUTA "SLIDES\\shade exel.SLD"))
 (end_image)
 (start_image "poli")  
 (slide_image 1 1 width height (STRCAT RUTA "SLIDES\\linea puntos.SLD"))
 (end_image)
 (start_image "grd")  
 (slide_image 1 1 width height (STRCAT RUTA "SLIDES\\c3d.SLD"))
 (end_image)
 (start_image "opciones")  
 (slide_image 1 1 width height (STRCAT RUTA "SLIDES\\PERF-OP.sld"))
 (end_image)

  (action_tile "arcsv" "(v1)")
  (action_tile "poli" "(v2)")
  (action_tile "grd" "(v3)")
  (action_tile "opciones" "(v4)")
  (action_tile "cancel" "(exit)")
  (start_dialog)                          
                                          
  (unload_dialog dcl_id)                  
  (princ)
  (setq r 0)
  (if (and (= (strcase res) "A") (= r 0))
    (PROGN
      (SETQ OPTPERF 0)
      (c:cpo)
      (setq r 1)
    )  
  )
  (if (= (strcase res) "P")
    (perfIL)
    (IF (AND (/= (strcase res) "P") (/= (strcase res) "A"))
     (perfsurf1)
    )
  )
  (setq emin nil)
  (setq emax nil)
)

(DEFUN MPUN (POLI)
  (SETQ PROV 1)
  (SETQ P1 (VERTICE POLI PROV))
  (WHILE P1
    (command "ZOOM" "W" (suma p1 0.10 0.10) (suma p1 -0.10 -0.10))
    (setq gpoLP (ssget "C" (suma p1 0.10 0.10) (suma p1 -0.10 -0.10)))
    (SETQ R (sslength gpoLP))
    (SETQ PROV2 0)
    (setq mdist 100)
    (REPEAT R
      (SETQ OBJ (ssname gpoLP PROV2))
      (if (= NOMBLO (cdr (assoc 2 (entget OBJ))))
       (progn
        (SETQ PV (cdr (assoc 10 (entget OBJ))))
        (setq pdist (distance p1 pv))
        (if (> mdist pdist)
         (progn
          (setq mdist pdist)
          (setq obcor obj)
         )
        )
       )
      )
      (SETQ PROV2 (1+ PROV2))
    )
    (if (/= obcor nil)
      (PROGN
       (command "MOVE" OBCOR "" (cdr (assoc 10 (entget OBCOR))) P1)
       (SETQ OBCOR NIL)
      )
    )
    (SETQ PROV (1+ PROV))
    (SETQ P1 (VERTICE POLI PROV))
  )
)

(DEFUN BUSATR (E ATR)
 (SETQ E (ENTNEXT E))
 (SETQ R 0)
 (WHILE (= "ATTRIB" (cdr (assoc 0 (entget E))))
   (if (= "ATTRIB" (cdr (assoc 0 (entget E))))
      (if (= ATR (cdr (assoc 2 (entget E))))
       (PROGN
        (setq vALAT (cdr (assoc 1 (entget E))))
       )
      )
   )
   (SETQ R (1+ R))
   (SETQ E (ENTNEXT E))
 )
 (PRINT ValAT)
)

(defun verticeSURF (poli nov)
  (C:LIBRERIA "BUSCA VALOR DE ATRIBUTO")
  (setq listap (entget poli))
  (setq nver 0)
  (setq salir "N")
  (while (= salir "N")
    (setq sublisp (car listap))
    (if (= 10 (car sublisp))
      (progn
        (setq punto (cdr sublisp))   
        (setq nver (+ nver 1))
      )
    )
    (setq listap (cdr listap))
    (if listap
      (setq salir "N")
      (setq salir "S")
    )
    (if (= nov nver)
      (setq salir "S")
    )
  )
  (if (not listap)
    (setq punto nil)
  )
  (setq punto punto)
)

(DEFUN PERFSURF1 ()
  (setq lin (car (entsel "\n Selecciona la polylinea a procesar: ")))
  (SETQ ARRANQUE 1000)
  (while (/= "LWPOLYLINE" (cdr (assoc 0 (entget lin))))
      (if (/= "LWPOLYLINE" (cdr (assoc 0 (entget lin))))
        (progn   
          (alert "\nEl objeto debe ser polylinea ")
          (setq lin (car (entsel "\n Selecciona objeto: ")))
        )
      )
  )
  (setq arcdes (strcat ruta "PERF.BLN"))
    (setq f 0)
    (SETQ VER1 "")
    (while ver1
       (setq f (1+ f))
       (SETQ VER1 (verticeSURF lin f)) 
    )
    (setq f (1- f))
    (SETQ f1 (OPEN arcdes "w"))
    (WRITE-LINE (STRCAT (RTOS F 2 0) ", 0" ) F1)
    (setq J 0)
    (REPEAT F
       (setq J (1+ J))
       (PRINT J)
       (SETQ VER1 (verticeSURF lin J))
       (IF (/= VER1 NIL)
         (write-line (strcat (rtos (car ver1) 2 3) "," (rtos (car (cdr ver1)) 2 3)) F1)
       )
    )
  (CLOSE F1)
  (setq GRDFILE (getfiled "ARCHIVO GRID FUENTE" "C:\\TOPOGRAF\\" "GRD" 18))
  (SETQ FGRD (OPEN (strcat ruta "GRD.GRI") "w"))
  (WRITE-LINE GRDFILE FGRD)
  (CLOSE FGRD)
  (COMMAND "SHELL" (strcat "C:\\Progra~1\\Golden~1\\Surfer8\\Scripter\\Scripter.exe -x " RUTA "PERFS.BAS"))
  (LOAD (STRCAT RUTAFAS "PERF"))
  (SETQ OPTPERF 1)
  (SETQ NOMARCH (strcat ruta "PERF2.CSV"))
  (C:CPO)
)

(DEFUN EXLAYER (LAYBUS)
   (SETQ LAYPROV (tblnext "layer" T))
   (SETQ FIND "N")
   (WHILE LAYPROV
     (IF (= (cdr (assoc 2 LAYPROV)) LAYBUS)
       (PROGN
         (SETQ LAYPROV NIL)
         (SETQ FIND "S")
       )
       (SETQ LAYPROV (tblnext "layer"))
     )
   )
   (PRINT FIND)
)

(defun v1 ()
  (setq res "A")
  (done_dialog)
)

(defun v2 ()
  (setq res "P")
  (done_dialog)
)

(defun v3 ()
  (setq res "G")
  (done_dialog)
)

(defun v4 ()
  (if (not (new_dialog "perf2" dcl_id))   
    (exit)                                
                                          
  )
  (set_tile "defx" defx)
  (set_tile "defy" defy)
  (set_tile "sepy" sepelev2)
  (set_tile "sepx" sepcad)
  (set_tile "op1" opcprog)
  (action_tile "accept" "(leevar)")
  (action_tile "cade" "(opcade)")
  (action_tile "elev" "(opelev)")
  (action_tile "elev2" "(opelev2)")
  (action_tile "ret" "(oplret)")
  (action_tile "tn" "(opltn)")
  (action_tile "env" "(oplenv)")
  (start_dialog)                          

  (if (not (new_dialog "perf" dcl_id))   
    (exit)                                
                                          
  )
  (setq width (dimx_tile  "arcsv")
        height (dimy_tile "arcsv"))
  (start_image "arcsv")  
  (slide_image 1 1 width height (STRCAT RUTA "SLIDES\\shade exel.SLD"))
  (end_image)
  (start_image "poli")  
  (slide_image 1 1 width height (STRCAT RUTA "SLIDES\\linea puntos.SLD"))
  (end_image)
  (start_image "grd")  
  (slide_image 1 1 width height (STRCAT RUTA "SLIDES\\c3d.SLD"))
  (end_image)
  (start_image "opciones")  
  (slide_image 1 1 width height (STRCAT RUTA "SLIDES\\PERF-OP.sld"))
  (end_image)

  (action_tile "arcsv" "(v1)")
  (action_tile "poli" "(v2)")
  (action_tile "grd" "(v3)")
  (action_tile "opciones" "(v4)")
  (action_tile "cancel" "(exit)")
  (start_dialog)                          
)

(defun leevar () 
  (setq defx (get_tile "defx"))
  (setq defy (get_tile "defy"))
  (setq sepelev2 (get_tile "sepy"))
  (setq sepcad (get_tile "sepx"))
  (setq opcprog (get_tile "op1"))
  (setq ARCINSAT (open (strcat ruta "configuraciones de programas\\perfil.CFG") "w"))
  (write-line ttcad arcinsat)
  (write-line ftcad arcinsat)
  (write-line ctcad arcinsat)
  (write-line ttcot arcinsat)
  (write-line ftcot arcinsat)
  (write-line ctcot arcinsat)
  (write-line ttest arcinsat)
  (write-line ftest arcinsat)
  (write-line ctest arcinsat)
  (write-line tlret arcinsat)
  (write-line alret arcinsat)
  (write-line clret arcinsat)
  (write-line tltn arcinsat)
  (write-line altn arcinsat)
  (write-line cltn arcinsat)
  (write-line tlenv arcinsat)
  (write-line alenv arcinsat)
  (write-line clenv arcinsat)
  (write-line defx arcinsat)
  (write-line defy arcinsat)
  (write-line sepelev2 arcinsat)
  (write-line sepcad arcinsat)
  (write-line opcprog arcinsat)
  (CLOSE ARCINSAT)
  (done_dialog)
)

(defun opcade () 
  (if (not (new_dialog "perf3" dcl_id))   
    (exit)                                
                                          
  )
  (set_tile "stext" ttcad)
 (setq width (dimx_tile  "color")
       height (dimy_tile "color"))
 (start_image "color")
 (fill_image 0 0 width height (atoi ctcad))   ;1 = AutoCAD red.
 (end_image)
  (set_tile "color2" ctcad)
  (action_tile "accept" "(leevar2)")
  (action_tile "color" "(leecolor ctcad)")
  (start_dialog)                          
)

(defun opelev () 
  (if (not (new_dialog "perf3" dcl_id))   
    (exit)                                
                                          
  )
  (set_tile "stext" ttcot)
 (setq width (dimx_tile  "color")
       height (dimy_tile "color"))
 (start_image "color")
 (fill_image 0 0 width height (atoi ctcot))   ;1 = AutoCAD red.
 (end_image)
  (set_tile "color2" ctcot)
  (action_tile "accept" "(leevar3)")
  (action_tile "color" "(leecolor ctcot)")
  (start_dialog)                          
)

(defun opelev2 () 
  (if (not (new_dialog "perf3" dcl_id))   
    (exit)                                
                                          
  )
  (set_tile "stext" ttest)
 (setq width (dimx_tile  "color")
       height (dimy_tile "color"))
 (start_image "color")
 (fill_image 0 0 width height (atoi ctest))   
 (end_image)
  (set_tile "color2" ctest)
  (action_tile "accept" "(leevar4)")
  (action_tile "color" "(leecolor ctest)")
  (start_dialog)                          
)

(defun leevar2 () 
  (setq ttcad (get_tile "stext"))
  (setq ctcad (get_tile "color2"))
  (done_dialog)
)

(defun leecolor (color) 
  (setq colorx color)
  (setq color (acad_colordlg (atoi color)))
  (if (= color nil) (setq color colorx) (setq color (itoa color)))
  (setq width (dimx_tile  "color")
        height (dimy_tile "color"))
  (start_image "color")
  (fill_image 0 0 width height (atoi color))
  (end_image)
  (set_tile "color2" color)
)

(defun leevar3 () 
  (setq ttcot (get_tile "stext"))
  (setq ctcot (get_tile "color2"))
  (done_dialog)
)

(defun leevar4 () 
  (setq ttest (get_tile "stext"))
  (setq ctest (get_tile "color2"))
  (done_dialog)
)

(defun oplret () 
  (if (not (new_dialog "perf4" dcl_id))   
    (exit)                                
                                          
  )
  (if (= tlret "1")
     (set_tile "cont" "1")
     (set_tile "disc" "1")
  )
  (set_tile "anchl" alret)
  (setq width (dimx_tile  "color")
        height (dimy_tile "color"))
  (start_image "color")
  (fill_image 0 0 width height (atoi clret))   
  (end_image)
  (set_tile "color2" clret)
  (action_tile "accept" "(leevar5)")
  (action_tile "color" "(leecolor clret)")
  (start_dialog)                          
)

(defun leevar5 () 
  (if (= (get_tile "cont") "1")
     (setq tlret "1")
  )
  (if (= (get_tile "disc") "1")
     (setq tlret "2")
  )
  (setq alret (get_tile "anchl"))
  (setq clret (get_tile "color2"))
  (done_dialog)
)

(defun opltn () 
  (if (not (new_dialog "perf4" dcl_id))   
    (exit)                                
                                          
  )
  (if (= tltn "1")
     (set_tile "cont" "1")
     (set_tile "disc" "1")
  )
  (set_tile "anchl" altn)
  (setq width (dimx_tile  "color")
        height (dimy_tile "color"))
  (start_image "color")
  (fill_image 0 0 width height (atoi cltn))   
  (end_image)
  (set_tile "color2" cltn)
  (action_tile "accept" "(leevar6)")
  (action_tile "color" "(leecolor cltn)")
  (start_dialog)                          
)

(defun leevar6 () 
  (if (= (get_tile "cont") "1")
     (setq tltn "1")
  )
  (if (= (get_tile "disc") "1")
     (setq tltn "2")
  )
  (setq altn (get_tile "anchl"))
  (setq cltn (get_tile "color2"))
  (done_dialog)
)

(defun oplenv () 
  (if (not (new_dialog "perf4" dcl_id))   
    (exit)                                
                                          
  )
  (if (= tlenv "1")
     (set_tile "cont" "1")
     (set_tile "disc" "1")
  )
  (set_tile "anchl" altn)
  (setq width (dimx_tile  "color")
        height (dimy_tile "color"))
  (start_image "color")
  (fill_image 0 0 width height (atoi clenv))   
  (end_image)
  (set_tile "color2" clenv)
  (action_tile "accept" "(leevar7)")
  (action_tile "color" "(leecolor clenv)")
  (start_dialog)                          
)

(defun leevar7 () 
  (if (= (get_tile "cont") "1")
     (setq tlenv "1")
  )
  (if (= (get_tile "disc") "1")
     (setq tlenv "2")
  )
  (setq alenv (get_tile "anchl"))
  (setq clenv (get_tile "color2"))
  (done_dialog)
)
