(defun CadNum (NOMBRE)
  (SETQ LNG (STRLEN NOMBRE))
  (SETQ NOMBLO "")
  (SETQ CONT 0)
  (REPEAT LNG
    (SETQ CONT (1+ CONT))
    (setq CARACTER (substr NOMBRE CONT 1))
    (IF (= CARACTER "+") (SETQ CARACTER ""))
    (setq nomblo (STRCAT NOMBLO CARACTER))
  )
  (setq CadNumVar NomBlo)
)

(defun valcap (NL)
  (setq prov2 1)
  (while (/= "." (substr NL prov2 1))
    (setq prov2(1+ prov2))
  )
  (setq NL (strcat (substr NL 1 (1- prov2)) "-" (substr NL (1+ prov2) 3)))
  (setq valcap NL)
)

(defun C:CreaCFG ()
  (setq AncSec (getint "Ancho total de la Seccion: "))

  (setq SepLiH (getreal "Separacion Hor. de Lineas: "))
  (setq SepTeH (getint "Etiquetar a cada numero de lineas: "))

  (setq SepLiV (getreal "Separacion Ver. de lineas: "))
  (setq SepTeV (getint "Etiquetar a cada numero de lineas: "))

  (setq ArcDes nil)
  (while (= ArcDes nil)
    (setq ArcDeS (getfiled "ARCHIVO DE DESCARGA DE DATOS POR SECCION: " "*." "CSV" 19))
  )
  (setq CapTeN (getstring "Capa Terreno Natural: <TN> "))
  (if (= CapTeN "")
    (setq CapTeN "TN")
    (progn
      (setq VC CapTeN)
      (setq NVC (valcad CapTeN))
      (if (/= VC NCV)
        (progn
          (getstring (strcat "Se cambio el nombre de la capa de: " VC " a: " NVC " preciona ENTER"))
          (setq CapTeN NVC)
        )
      )
    )
  )
  (setq CapLiR (getstring "Capa Lineas de retícula en: <Reticula>"))
  (if (= CapLiR "")
    (setq CapLiR "Reticula")
    (progn
      (setq VC CapLiR)
      (setq NVC (valcad CapLiR))
      (if (/= VC NCV)
        (progn
          (getstring (strcat "Se cambio el nombre de la capa de: " VC " a: " NVC " preciona ENTER"))
          (setq CapLiR NCV)
        ) 
      )
    )
  )
  (setq CapTeR (getstring "Capa Textos de retícula en: <Reticula>"))
  (if (= CapTeR "")
    (setq CapTeR "Reticula")
    (progn
      (setq VC CapTeR)
      (setq NVC (valcad CapTeR))
      (if (/= VC NCV)
        (progn
          (getstring (strcat "Se cambio el nombre de la capa de: " VC " a: " NVC " preciona ENTER"))
          (setq CapTeR NCV)
        ) 
      )
    )
  )
  (setq CapCad (getstring "Capa de cadenamientos: <TN>"))
  (if (= CapCad "")
    (setq CapCad "TN")
    (progn
      (setq VC CapTeR)
      (setq NVC (valcad CapCad))
      (if (/= VC NCV)
        (progn
          (getstring (strcat "Se cambio el nombre de la capa de: " VC " a: " NVC " preciona ENTER"))
          (setq CapCad NCV)
        ) 
      )
    )
  )
  (setq CapCot (getstring "Capa de cotas: <TN>"))
  (if (= CapCot "")
    (setq CapCot "TN")
    (progn
      (setq VC CapCot)
      (setq NVC (valcad CapCot))
      (if (/= VC NCV)
        (progn
          (getstring (strcat "Se cambio el nombre de la capa de: " VC " a: " NVC " preciona ENTER"))
          (setq CapCot NCV)
        ) 
      )
    )
  )
  (setq ArcCon (open "c:\\Archivos de Programa\\AutoCAD R14\\ConfiSec.txt" "w"))
  (write-line (strcat "Ancho total de Sección: " (itoa AncSec)) ArcCon)
  (write-line (strcat "Separación Hor. de Líneas: " (rtos SepLiH)) ArcCon)
  (write-line (strcat "Separación Hor. de Textos: " (itoa SepTeH)) ArcCon)
  (write-line (strcat "Separación Ver. de líneas: " (rtos SepLiV)) ArcCon)
  (write-line (strcat "Separación Ver. de Textos: " (itoa SepTeV)) ArcCon)
  (write-line (strcat "Archivo a descargar datos: " ArcDeS) ArcCon)
  (write-line (strcat "Terreno Natural: " CapTeN) ArcCon)
  (write-line (strcat "Lineas de retícula en: " CapLiR) ArcCon)
  (write-line (strcat "Textos de retícula en: " CapTeR) ArcCon)
  (write-line (strcat "Cadenamiento en: " CapCad) ArcCon)
  (write-line (strcat "Cota en: " CapCot) ArcCon)
  (close ArcCon)
)


(defun suma (punto xx yy)
  (setq xxx (car punto))
  (setq yyy (car (cdr punto)))
  (setq xxx (+ xxx xx))
  (setq yyy (+ yyy yy))
  (list xxx yyy)
)

(defun asigna ()
  (setq xm (car (cdr (assoc 10 (entget ob)))))
  (setq xml ele2)
)

(defun redo5 (daton)
  (setq daton (rtos daton 2 3))
  (setq cara (substr daton 1 1))
  (setq cuecar 1)
  (setq encpun 0)
  (setq pospun 0)
  (while (/= cara "")
    (setq cara (substr daton cuecar 1))
    (if (= cara ".")
      (progn
        (setq encpun 1)
        (setq pospun cuecar)
      )
    )
    (setq cuecar (+ cuecar 1))
  )    
  (if (= encpun 1)
    (progn
      (if (= (strlen daton) 1)            
        (setq daton daton)
      )
      (setq numdec (strlen (substr daton pospun)))
      (setq daton (substr daton 1 (- (strlen daton) numdec)))
    )
    (setq daton daton)
  )

;  (setq ultimo (atof (substr daton (strlen daton) 1)))
;  (if (/= ultimo 0)
;    (progn
;      (setq inicio (substr daton 1 (- (strlen daton) 1)))
;      (if (> 6 ultimo)
;        (setq daton (atof (strcat inicio "5")))
;        (setq daton (+ (atof (strcat inicio "0")) 10))
;      )
;    )
;    (setq daton (atof daton))
;  )
  (setq daton (atof daton))
)


(defun ordenax ()
  (setq ele2 0)
  (setq xlm 0)
  (setq ob (ssname gpo ele2))
  (setq xm (car (cdr (assoc 10 (entget ob)))))  
  (while ob
    (if (>= (car (cdr (assoc 10 (entget ob)))) xm)
      (asigna)
    )
    (setq ele2 (+ ele2 1))
    (setq ob (ssname gpo ele2))
  )
)

(defun cadena ()
  (setq cad ob)
  (setq cadtex (cdr (assoc 1 (entget cad))))
  (setq numtxt ele)
)

(defun ordena ()
  (setq ele 0)
  (setq ob (ssname gpo ele))
  (while ob
    (if (= "LINE" (cdr (assoc 0 (entget ob))))
      (setq numli ele)
    )
    (if (= "TEXT" (cdr (assoc 0 (entget ob))))
      (cadena)
    )
    (setq ele (+ ele 1))
    (setq ob (ssname gpo ele))
  )
  (setq gpoo (ssadd (ssname gpo numtxt)))
  (setq gpoo (ssadd (ssname gpo numli)))
  (ssdel (ssname gpo numli) gpo)
  (if (> numtxt numli)
    (setq numtxt (- numtxt 1))
  )
  (ssdel (ssname gpo numtxt) gpo)

  (setq ele 0)
  (setq ele2 0)
  (setq ob (ssname gpo ele))
  (while (/= ele (- eleme 2))
    (ordenax)
    (ssadd (ssname gpo xml) gpoo)
    (ssdel (ssname gpo xml) gpo)
    (setq ele (+ ele 1))
  )
)

(defun ordena2 ()
  (setq ele 0)
  (setq ob (ssname gpo ele))
  (while ob
    (if (= "LINE" (cdr (assoc 0 (entget ob))))
      (setq numli ele)
    )
    (setq ele (+ ele 1))
    (setq ob (ssname gpo ele))
  )
  (setq gpoo (ssadd (ssname gpo numli)))
  (ssdel (ssname gpo numli) gpo)

  (setq ele 0)
  (setq ele2 0)
  (setq ob (ssname gpo ele))
  (while (/= ele (- eleme 1))
    (ordenax)
    (ssadd (ssname gpo xml) gpoo)
    (ssdel (ssname gpo xml) gpo)
    (setq ele (+ ele 1))
  )
)


(defun ver1 ()
  (setq ele 0)
  (setq ob (ssname gpoo ele))
  (while ob
    (prin1 (entget ob))
    (write-line " ")
    (setq ele (+ ele 1))
    (setq ob (ssname gpoo ele))
  )
)

(defun ver2 ()
  (setq ele 0)
  (setq ob (ssname gpo ele))
  (while ob
    (prin1 (entget ob))
    (write-line " ")
    (setq ele (+ ele 1))
    (setq ob (ssname gpo ele))
  )
)

(defun mueve ()
  (setq p11 (suma (cdr (assoc 10 (entget (ssname gpoo 0)))) 0.1 0.1))
  (setq p12 (suma (cdr (assoc 10 (entget (ssname gpoo 0)))) -0.1 -0.1))
  (command "ZOOM" "w" p11 p12)
;  (SETQ GPO (ENTGET CAD))
;  (PRINT GPO)
;  (SETQ XOB1 (CDR (assoc 10 (entget (ssname GPO 0)))))
;  (SETQ XOB2 (CDR (assoc 10 (entget (ssname GPO (sslength GPO))))))
;  (SETQ PX1 (CAR XOB1))
;  (SETQ PY1 (CADR XOB1))
;  (SETQ PX2 (CAR XOB2))
;  (SETQ PY2 (CADR XOB2))
;  (IF (= PX1 PX2)
;    (SETQ MX PX1)
;    (SETQ MX (/ (ABS (- PX1 PX2)) 2))
;  )
;  (IF (= PY1 PY2)
;    (SETQ MY PY1)
;    (SETQ MY (/ (ABS (- PY1 PY2)) 2))
;  )
;  (IF (> PX1 PX2)
;    (SETQ MX (+ PX2 MX))
;    (SETQ MX (+ PX1 MX))
;  )
;  (IF (> PY1 PY2)
;    (SETQ MY (+ PY2 MY))
;    (SETQ MY (+ PY1 MY))
;  )
;  (SETQ MY (RTOS MY 2 6))
;  (SETQ MX (RTOS MX 2 6))
;  (SETQ MITAD (STRCAT MX "," MY))
;  (command "MOVE" gpoo cad "" MITAD "0,0")
  (setq ligpoo (ssname gpoo 0))
  (setq pun1 (cdr (assoc 10 (entget ligpoo)))) 
  (setq pun2 (cdr (assoc 11 (entget ligpoo)))) 
  (setq x1 (car pun1))
  (setq y1 (car (cdr pun1)))
  (setq x2 (car pun2))
  (setq y2 (car (cdr pun2)))
  (setq xd (- x1 x2))
  (if (> 0 xd)
    (setq xd (* xd -1))
  )
  (setq xd (/ xd 2))

  (setq yd (- y1 y2))
  (if (> 0 yd)
    (setq yd (* yd -1))
  )
  (setq yd (/ yd 2))
  (if (> x1 x2)
    (setq xd (+ xd x2))
    (setq xd (+ xd x1))
  )
  (if (> y1 y2)
    (setq yd (+ yd y2))
    (setq yd (+ yd y1))
  )
  (setq punmid (list xd yd))  

  (COMMAND "-LAYER" "SET" "PROV" "")
  (command "CIRCLE" PUNMID "1")
  (command "COPY" gpoo cad "" punmid punmid)
  (command "MOVE" gpoo cad "" punmid "0,0")
  (command "ZOOM" "c" "0,0" (+ (distance pun1 pun2) 6))
)

(defun rota ()
  (setq p1 (cdr (assoc 10 (entget (ssname gpoo 0)))))
  (setq p2 (cdr (assoc 11 (entget (ssname gpoo 0)))))
  (setq angulo (- 360.0 (atof (angtos (angle p1 p2) 0 8))))
  (command "ROTATE" gpoo cad "" "0,0" angulo)
  (setq r1 (getstring "\n Rotar 180 <N>:"))
  (if (= (strcase r1) "S")
    (command "ROTATE" gpoo cad "" "0,0" "180")
  )
)

(defun ez (obje)
  (setq obje (entnext obje))
  (if (= "ELEV" (strcase (cdr (assoc 2 (entget obje)))))
    (setq eleva (cdr (assoc 1 (entget obje))))
  )
  (setq obje (entnext obje))
  (if (= "ELEV" (strcase (cdr (assoc 2 (entget obje)))))
    (setq eleva (cdr (assoc 1 (entget obje))))
  )
  (setq obje (entnext obje))
  (if (= "ELEV" (strcase (cdr (assoc 2 (entget obje)))))
    (setq eleva (cdr (assoc 1 (entget obje))))
  )
  (setq elev (atof eleva))
)

(defun traza ()
  (setq ele 1)
  (setq ob1 (ssname gpoo ele))
  (setq p1 (cdr (assoc 10 (entget ob1))))
  (setq zm (ez ob1))
  (setq zn (ez ob1))
  (setq ob2 ob1)
  (setq salir 1)
  (setq gpoo2 (ssadd))
  (command "LAYER" "M" "SECCION" "")
  (command "LAYER" "S" "SECCION" "")
  (while salir
    (setq ele (+ ele 1))
    (setq ob2 (ssname gpoo ele))
    (setq p2 (cdr (assoc 10 (entget ob2))))
    (setq x1 (car p1))
    (setq x2 (car p2))
    (setq z1 (ez ob1))
    (setq z (ez ob2))
    (if (> z zm)
      (setq zm z)
    )
    (if (< z zn)
      (setq zn z)
    )
    (setq z2 (ez ob2))
    (setq p1r (list x1 z1))
    (setq p2r (list x2 z2))
    (COMMAND "-LAYER" "SET" CAPTEN "")
    (command "LINE" p1r p2r "")
    (ssadd (entlast) gpoo2)
    (setq p1 p2)
    (setq ob1 ob2)
    (setq salir (ssname gpoo (+ ele 1)))
  )
)


(defun inserta ()
  (setq cco (ssname gpoo 1))
  (setq cco (entnext cco)) (setq cco (entnext cco))
  (setq cco (cdr (assoc 1 (entget cco))))
  (setq cco (- (atof cco) 3.5))
  (setq cco2 (- cco 5))
  (setq cco3 (- cco 10))
  (command "LINE" (strcat "0," (rtos (- cco3 1000) 2 2)) "@9000<90" "")
  (setq linv (entlast))
  (setq pl1 (cdr (assoc 10 (entget linv))))
  (setq pl2 (cdr (assoc 11 (entget linv))))
  (setq lina (ssname gpoo2 0))
  (setq cuenta 0)
  (while (/= cuenta (sslength gpoo2))
    (setq pl3 (cdr (assoc 10 (entget lina))))
    (setq pl4 (cdr (assoc 11 (entget lina))))
    (setq nivel (inters pl1 pl2 pl3 pl4 T))
    (setq cuenta (+ cuenta 1))
    (setq lina (ssname gpoo2 cuenta))
    (if nivel
      (setq cuenta (sslength gpoo2))
    )
  )
  (setq ycco1 (+ cco 10)) (setq ycco2 (- cco 10))
  (command "ZOOM" "W" (strcat (rtos (+ ancho 20)) "," (rtos ycco1 2 2)) (strcat (rtos (* (+ ancho 20) -1)) "," (rtos ycco2 2 2)))
  (command "VIEW" "S" "S")
  (setq cco (strcat "0," (rtos cco 2 2)))
  (setq nivel2 (car (cdr nivel)))
  (SETQ NIVEL2 (rtos nivel2 2 3)) 
  (COMMAND "INSERT" "ELEV" (STRCAT "0," NIVEL2) "" "" "" "1" "1" "1" "" "" "")
  (SSADD (ENTLAST) GPORET)
  (setq bl (entnext (ENTLAST)))
  (COMMAND "attedit" "" "" "" "" bl "V" "R" NIVEL2 "")
  (setq bl (entnext BL))
  (COMMAND "attedit" "" "" "" "" bl "V" "R" "0" "")
  (setq bl (entnext BL))
  (COMMAND "attedit" "" "" "" "" bl "V" "R" CADTEXT "")
  (setq cadtexx (CadNum cadtex))
)

(defun reticula ()
  (setq ym (car (cdr (assoc 10 (entget (ssname gpoo2 0))))))
  (setq yn (car (cdr (assoc 11 (entget (ssname gpoo2 (- (sslength gpoo2) 1)))))))
;  (setq ym1 (atof (rtos (+ ym 1) 2 0)))
;  (setq yn1 (atof (rtos (- yn 1) 2 0)))
  (setq ym1 ancho)
  (setq yn1 ancho)
  (setq zm1 (redo5 (+ zm 1)))
  (setq zn1 (redo5 (- zn 2)))
  (setq gporet (ssadd))
  (command "LAYER" "M" "RETICULA" "")
  (command "LAYER" "S" "RETICULA" "")
;  (command "LINE" (strcat "0," (rtos zn1)) (strcat "0," (rtos (- zm1 1))) "")
;  (ssadd (entlast) gporet)
;  (command "LINE" (strcat (rtos yn1) "," (rtos (+ zn1 1))) (strcat (rtos ym1) "," (rtos (+ zn1 1))) "")
;  (ssadd (entlast) gporet)
  (setq picad (list 0 (+ zn1 1)))
;  (command "INSERT" "texto2" picad "" "" "")
;  (command "EXPLODE" (entlast))
;  (setq cadt (entlast))
;  (entmod (subst (cons 1 cadtex) (assoc 1 (entget cadt)) (entget cadt)))
  (setq love (- zm1 zn1 2))
  (setq loho (- ym1 yn1 1))
  (setq cuenta 0)
  (setq cuetex septex)
  (setq znn1 zn1)
  (setq zn1 (+ zn1 1))
  (while (<= zn1 zm1)
    (if (= cuetex septex)
      (progn
        (command "INSERT" "RETH" (strcat (rtos (* ancho -1)) "," (rtos (+ zn1 0))) "" "" "")
        (command "EXPLODE" (entlast) "")
        (entmod (subst (cons 1 (rtos (+ zn1 0) 2 2)) (assoc 1 (entget (entlast))) (entget (entlast))))
        (ssadd (entlast) gporet)
        (command "INSERT" "RETH2" (strcat (rtos ancho) "," (rtos (+ zn1 0))) "" "" "")
        (command "EXPLODE" (entlast) "")
        (entmod (subst (cons 1 (rtos (+ zn1 0) 2 2)) (assoc 1 (entget (entlast))) (entget (entlast))))
        (ssadd (entlast) gporet)
        (setq cuetex 0)
      )
    )
    (command "LINE" (strcat (rtos ancho) "," (rtos (+ zn1 0))) (strcat (rtos (* ancho -1)) "," (rtos (+ zn1 0))) "")
    (ssadd (entlast) gporet)
    (setq zn1 (+ zn1 sepret))
    (setq cuetex (+ cuetex 1))
    (setq cuenta (+ cuenta 1))
  )
  (setq altosec (* (- cuenta 1) sepret))
  (setq cuenta 0)
  (setq yma (car (cdr (cdr (assoc 10 (entget (entlast)))))))
  (setq cuetex2 septex2)
  (setq yn1 (- yn1 1))
  (while (> (+ yn1 1) (* (+ sepret ancho) -1))
;    (setq cuenta (+ cuenta 1))
;    (if (/= yn1 -1)
;      (progn
        (if (= cuetex2 septex2)
          (progn
            (command "INSERT" "RETV" (strcat (rtos (+ yn1 1)) "," (rtos (+ znn1 1))) "" "" "")
            (command "EXPLODE" (entlast) "")
            (entmod (subst (cons 1 (rtos (+ yn1 1) 2 0)) (assoc 1 (entget (entlast))) (entget (entlast))))
            (COMMAND "CHANGE" "L" "" "P" "LA" CapTer "")
            (ssadd (entlast) gporet)
            (setq cuetex2 0)
          )
        )
        (setq cuetex2 (+ cuetex2 1))
;      )
;    )
    (command "LINE" (strcat (rtos (+ yn1 1)) "," (rtos (+ znn1 1))) (strcat (rtos (+ yn1 1)) "," (rtos yma)) "")
    (ssadd (entlast) gporet)
    (setq yn1 (- yn1 sepret2))
  )
  (setq puninsblo (list yn1 zn1))
  (write-line (strcat (rtos nivel2 2 3) "," cadtexx "," (rtos altosec 2 2)) ArchS)
  (write-line (rtos altosec 2 2))
)


(defun bloque ()
  (command "ERASE" gpoo cad "")
    (setq cadtext nomcad)
    (SETQ LNG (STRLEN nomcad))
    (SETQ NOMBLO "")
    (SETQ CONT 0)
    (REPEAT LNG
        (SETQ CONT (1+ CONT))
        (setq CARACTER (substr CADTEXT CONT 1))
        (IF (= CARACTER "+") (SETQ CARACTER "-"))
        (setq nomblo (STRCAT NOMBLO CARACTER))
    )
  (command "BLOCK" nomblo "0,0" gpoo2 gporet cadt nivv "")
  (command "VIEW" "R" "C")
)

(defun borrar ()
  (setq r2 (getstring " Eliminar los datos en planta y crear bloque <S>:"))
  (if (= r2 "")
    (setq r2 "S")
  )
  (if (= (strcase r2) "S")
    (bloque)
  )
)

(defun agrega (entagr gpoagr)
  (setq tipagr (cdr (assoc 0 (entget entagr))))
  (setq cueagr 0)
  (while (/= cueagr (sslength gpoagr))
    (setq nomagr (ssname gpoagr cueagr))
    (if (= tipagr (cdr (assoc 0 (entget nomagr))))
      (progn
        (ssdel nomagr gpoagr)
        (setq cueagr (- cueagr 1))
      ) 
    )
    (setq cueagr (+ cueagr 1))
  )
  (ssadd entagr gpoagr)
  (setq agregavar gpoagr)
)


(defun filtro (gpofil)
  (setq cof 0)
  (setq cuelin 0)
  (setq cuetex 0)
  (while (/= cof (sslength gpofil))
    (setq eliobj "SI")
    (setq objfil (ssname gpofil cof))
    (if (= "LINE" (cdr (assoc 0 (entget objfil))))
      (progn
        (setq eliobj "NO")
        (setq cuelin (+ cuelin 1)) 
      ) 
    )
    (if (= "PUN2" (cdr (assoc 2 (entget objfil))))
      (setq eliobj "NO")
    )
    (if (= "TEXT" (cdr (assoc 0 (entget objfil))))
      (progn
        (setq eliobj "NO")
        (setq cuetex (+ cuetex 1)) 
      ) 
    )
    (if (= eliobj "SI")
      (progn
        (ssdel objfil gpofil)
        (setq cof (- cof 1))
      )
    )
    (setq cof (+ cof 1))
  )

  (if (> cuelin 1)
    (progn
      (alert "Se seleccionaron mas de una linea en el grupo")
      (setq tipent "X") 
      (while (/= "LINE" TipEnt)
        (setq lin (car (entsel "Selecciona la linea correspondiente")))
        (setq TipEnt (cdr (assoc 0 (entget lin)))) 
        (if (/= "LINE" TipEnt)
          (alert "La entidad que seleccionaste no es una linea")
        ) 
      ) 
      (setq gpofil (agrega lin gpofil))
    )
  )

  (if (= cuelin 0)
    (progn
      (alert "No se selecciono la linea de la seccion")
      (setq tipent "X") 
      (while (/= "LINE" TipEnt)
        (setq lin (car (entsel "Selecciona la linea correspondiente")))
        (setq TipEnt (cdr (assoc 0 (entget lin)))) 
        (if (/= "LINE" TipEnt)
          (alert "La entidad que seleccionaste no es una linea")
        ) 
      ) 
      (setq gpofil (agrega lin gpofil))
    )
  )

  (if (> cuetex 1)
    (progn
      (alert "Se seleccionaron mas de un texto en el grupo")
      (setq tipent "X") 
      (while (/= "TEXT" TipEnt)
        (setq lin (car (entsel "Selecciona el texto correspondiente (cadenamiento)")))
        (setq TipEnt (cdr (assoc 0 (entget lin)))) 
        (if (/= "TEXT" TipEnt)
          (alert "La entidad que seleccionaste no es un texto")
        ) 
      ) 
      (setq gpofil (agrega lin gpofil))
    )
  )

  (if (= cueTEX 0)
    (progn
      (alert "No se selecciono el texto del cadenamiento")
      (setq tipent "X") 
      (while (/= "TEXT" TipEnt)
        (setq lin (car (entsel "Selecciona el texto correspondiente")))
        (setq TipEnt (cdr (assoc 0 (entget lin)))) 
        (if (/= "TEXT" TipEnt)
          (alert "La entidad que seleccionaste no es un texto")
        ) 
      ) 
      (setq gpofil (agrega lin gpofil))
    )
  )

  (setq filtrovar gpofil)  
)

(defun c:se1 ()
  (setq os (getvar "osmode"))
  (command "OSNAP" "none")
  (setq haydat "Y")

  (if (not NomArcs)
    (setq haydat nil)
  )
  (if (not ancho)
    (setq haydat nil)
  )
  (if (not sepret)
    (setq haydat nil)
  )
  (if (not sepret2)
    (setq haydat nil)
  )
  (if (not septex)
    (setq haydat nil)
  )
  (if (not septex2)
    (setq haydat nil)
  )
  (if (= haydat nil)
    (progn
    (setq valida nil)
    (while (= valida nil)
      (setq arccon nil)
      (while (= arccon nil)
        (setq arccon (open "c:\\Archivos de Programa\\AutoCAD R14\\ConfiSec.Txt" "r"))
        (if (= arccon nil)
          (progn
            (getstring "No existe el archivo de configuracion del programa; se pediran los datos para crearlo ")
            (C:CreaCFG)
          )
        )
      )
      (write-line "Leeo datos de configuracion")
      (setq ancho (atof (substr (read-line arccon) 25)))
      (setq ancho (/ ancho 2))
      (setq sepret (atof (substr (read-line arccon) 28)))
      (setq septex (atof (substr (read-line arccon) 28)))
      (setq sepret2 (atof (substr (read-line arccon) 28)))
      (setq septex2 (atof (substr (read-line arccon) 28)))
      (setq NomArcS (substr (read-line arccon) 28))
      (setq CapTeN (substr (read-line arccon) 18))
      (setq CapLiR (substr (read-line arccon) 24))
      (setq CapTeR (substr (read-line arccon) 24))
      (setq CapCad (substr (read-line arccon) 18))
      (setq CapCot (substr (read-line arccon) 10))

      (setq valida "V")
      (if (= ancho 0)
        (setq valida nil)
      )
     (if (= sepret 0)
        (setq valida nil)
      )
      (if (= sepret2 0)
        (setq valida nil)
      )
      (if (= septex 0)
        (setq valida nil)
      )
      (if (= septex2 0)
        (setq valida nil)
      )
      (if (= NomArcS "")
        (setq valida nil)
      )
      (if (= CapTeN "")
        (setq valida nil)
      )
      (if (= CapLiR "")
        (setq valida nil)
      )
      (if (= CapTeR "")
        (setq valida nil)
      )
      (if (= CapCad "")
        (setq valida nil)
      )
      (if (= CapCot "")
        (setq valida nil)
      )
      (if (= valida nil)
        (C:CreaCFG)
      )
    (command "-layer" "N" CAPTEN "C" "GREEN" CAPTEN
    "N" CAPLIR "C" "YELLOW" CAPLIR 
    "N" CAPTER
    "N" CAPCAD
    "N" "PROV"
    "N" CAPCOT "")
    )
    )
  )
  (setq ArchS (open NomArcs "a"))
  (print "\n Seleciona los elementos a procesar ")
  (command "VIEW" "S" "C")
  (setq gpo (ssget))
  (setq gpo (filtro gpo))
  (setq eleme (sslength gpo))
  (setq gpoo (ssadd))
  (ordena)
  (setq nomcad (cdr (assoc 1 (entget cad))))
  (mueve)
  (rota)
  (setq eleme (- eleme 1))
  (setq gpo gpoo)
  (ordena2)
  (traza)
  (ver1)
  (inserta)
  (reticula)
  (borrar)
  (close archs)
  (setvar "osmode" os)
)

(defun c:RESE ()
  (setq ancho nil)
  (setq sepret nil)
  (setq sepret2 nil)
  (setq septex nil)
  (setq septex2 nil)
  (setq NomArcs nil)
  (write-line "Valores Reinicializados de secciones")
)

(defun cottopo (nume)
  (setq texto (rtos nume 2 0))
  (setq kilm 0)
  (if (= nume 0)
    (prin1 (setq resto "000"))
  )
  (if (> nume 9)
    (setq resto (strcat "0" texto))
  )
  (if (> nume 99)
   (setq resto texto)
  )
  (if (> nume 999)
    (progn
       (setq num1 (substr texto 1 1))
       (setq resto (substr texto 2 3))
    )
    (setq num1 "0")
  )
  (if (> nume 9999)
    (progn
      (setq num1 (substr texto 1 2))
      (setq resto (substr texto 3 3))
    )
  ) 
  (setq nuetex (strcat num1 "-" resto))
)

(defun DatC (linea nudato)
  (setq cuen 0)
  (setq cuecom 0)
  (setq salir "N")
  (setq cadena "")
  (while (/= salir "S")
    (setq cuen (+ cuen 1))
    (setq caracter (substr linea cuen 1))
    (if (= caracter ",")
      (setq cuecom (+ cuecom 1))
    )
    (if (= cuecom (- nudato 1))
      (if (/= caracter ",")
        (setq cadena (strcat cadena caracter))
      )
    )
    (if (or (= cuecom nudato) (>= cuen (strlen linea)))
      (setq salir "S")
    )
  )
  (setq cadena cadena)
)


(defun c:DESSEC ()
  (if (not NomArcs)
    (progn
      (setq NOMARCS (getfiled " Nombre del archivo a extraer alto de seccion: " "*." "CSV" 18))
    )
  )
  (setq ArchS (open NomArcs "r"))
  (PRINT ARCHS)
  (setq inc (getint " Incremento: "))
  (setq sepsecf (getreal " Separaci¢n entre filas: "))

  (setq pun (getpoint " Punto de inicio de descarga: "))
  (setq ypuno (car (cdr pun)))
  (setq SecCol 0)
  (setq CueSec 1)
  (setq lin (read-line ArchS))
  (while lin
    (setq lin (read-line ArchS))
    (setq alto (atof (DatC lin 3)))
    (command "INSERT" (cottopo SecCol) pun "" "" "")
    (setq CueSec (+ CueSec 1))
    (setq SecCol (+ SecCol inc))
    (setq xpun (car pun))
    (setq ypun (car (cdr pun)))
    (setq ypun (+ ypun sepsecf alto))
;    (if (= CueSec (+ NumSec 1))
;      (progn
;        (setq xpun (+ xpun (* (+ ancho sepsecc) 2)))
;        (setq CueSec 1)
;        (setq ypun ypuno)
;      )
;    )
    (setq pun (list xpun ypun))
  )
)
