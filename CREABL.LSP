(defun c:CREABL ()
    (setq texto (car (entsel "Selecciona EL TEXTO: ")))
    (setq NOMBRE (cdr (assoc 1 (entget TEXTO))))
    (SETQ LNG (STRLEN NOMBRE))
    (SETQ NOMBLO "")
    (SETQ CONT 0)
    (REPEAT LNG
        (SETQ CONT (1+ CONT))
        (setq CARACTER (substr NOMBRE CONT 1))
        (IF (= CARACTER "+") (SETQ CARACTER "-"))
        (IF (= CARACTER ".") (SETQ CARACTER "_"))
        (setq nomblo (STRCAT NOMBLO CARACTER))
    )
    (COMMAND "INSERT" NOMBRE "0,0" "" "" "")
    (COMMAND "EXPLODE" "L" "")
    (COMMAND "BLOCK" (STRCAT NOMBLO "-B") "0,0" "")
)
