(defun c:acot ()
  (COMMAND "UNDO" "M")
  (setq linea (car (entsel "\n Selecciona la linea a dimensionar "))) 
  (setq escala (getreal "\n Tamaño del texto "))
  (setq TipEnt (cdr (assoc 0 (entget linea)))) 
  (setq tipent (strcase tipent))
  (if (and (/= "LWPOLYLINE" TipEnt) (/= "LINE" TipEnt) (/= "ARC" TipEnt))
    (alert "La entidad que seleccionaste no es una linea")
  ) 
  (command "copy" linea "" "0,0" "0,0")
  (SETQ PRV (cdr (assoc 0 (entget linea))))
  (SETQ PRV (STRCASE PRV))
  (IF (=  PRV "LWPOLYLINE") 
    (PROGN
      (command "explode" (entlast) "")
      (setq gpoacot (ssadd))
      (setq gpoacot (ssget "p"))
    )
    (SETQ GPOACOt (SSADD LINEA))
  )
  (SETQ E (SSNAME GPOACOT 0))
  (setq cont 0)
  (WHILE E
    (SETQ PRV (cdr (assoc 0 (entget E))))
    (SETQ PRV (STRCASE PRV))
    (IF (= PRV "ARC")
      (PROGN
        (SETQ RADIO (cdr (assoc 40 (entget e))))
        (SETQ RADIOx (cdr (assoc 10 (entget e))))
        (SETQ Yr (CADR radiox))
        (SETQ Xr (CAR radiox))
        (SETQ ANGINI (cdr (assoc 50 (entget e))))
        (SETQ ANGF (cdr (assoc 51 (entget e))))
        (setq xc1 (+ xr (* radio (cos angini))))
        (setq yc1 (+ yr (* radio (sin angini))))
        (setq xc2 (+ xr (* radio (cos angf))))
        (setq yc2 (+ yr (* radio (sin angf))))
        (setq xyz (list xc1 yc1))
        (setq xyz2 (list xc2 yc2))
        (IF (< ANGINI ANGF)
          (PROGN
            (SETQ DIF (- ANGF ANGINI))
            (setq ang2 (+ angini (/ dif 2)))
          )
          (PROGN
            (SETQ ANGF (+ ANGF 6.28318))
            (SETQ DIF (- ANGF ANGINI))
            (setq ang2 (+ angini (/ dif 2)))
          )
        )
        (setq xc3 (+ xr (* radio (cos ang2))))
        (setq yc3 (+ yr (* radio (sin ang2))))
        (SETQ DISTANCIA (* RADIO DIF))
      )
      (progn
        (SETQ xyz (cdr (assoc 10 (entget e))))
        (SETQ xyz2 (cdr (assoc 11 (entget e))))
        (setq distancia (distance xyz xyz2))
      )
    )
  (setq distancia2 (distance xyz xyz2))
  (IF (= PRV "ARC")
    (progn 
      (setq ang (angle xyz xyz2))
      (setq ang (* 180 (/ ang pi)))
      (command "INSERT" (STRCAT RUTA "BLOCKS\\COTA") (list xc3 yc3) escala "" ang "" "")
    )
    (progn 
      (command "INSERT" (STRCAT RUTA "BLOCKS\\COTA") (polar XYZ (angle XYZ XYZ2) (/ DISTANCIA2 2)) escala "" xyz2 "" "")
    )
  )
  (SETQ ENTP (ENTLAST))
  (SETQ ENTP (ENTNEXT ENTP))
  (SETQ DISTANCIAXX (ATOF (RTOS DISTANCIA 2 0)))
  (IF (< DISTANCIAXX DISTANCIA)
    (SETQ DISTANCIA (1+ DISTANCIA)) 
  )
  (COMMAND "ATTEDIT" "" "" "" "" ENTP "V" "R" (rtos distancia 2 0) "")
  (SETQ CONT (1+ CONT))
  (SETQ E (SSNAME GPOACOT cont))
  )
  (command "erase" gpoacot "")
)
