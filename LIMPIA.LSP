(DEFUN C:LIMPI ()
  (IF (= LAYCONG NIL) (SETQ LAYCONG "GSLAYER"))
  (IF (/= VLIMPIA 1)
   (PROGN  
    (SETQ LAYCONG "GSLAYER")
    (COMMAND "UNDO" "M")
    (setq na (car (entsel "\n Selecciona la linea ")))
    (setq p1 (getpoint "\n Punto exterior "))
   )
  )
  (setq layer (cdr (assoc 8 (entget na))))
  (if (/= LAYCONG layer)
    (command "change" na "" "P" "LA" LAYCONG "")
  )
  (COMMAND "-LAYER" "SET" LAYCONG "FR" "*" "")
  (command "expresstools")
  (load (strcat ruta "exlimpia"))
  (c:extrim2)
  (SETQ PROV 1)
  (SETQ VER1 (verticesurf na prov))
  (COMMAND "ERASE" "ALL" "R" "CP")
  (WHILE VER1
     (IF (/= VER1 NIL)
      (progn
        (SETQ Y (CADR ver1))
        (SETQ Y (RTOS Y 2 3))
        (SETQ X (CAR ver1))
        (SETQ X (RTOS X 2 3))
        (PRINT (STRCAT X "," Y))
        (COMMAND (STRCAT X "," Y))
      )
      (COMMAND "")
     )
     (SETQ PROV (1+ PROV))
     (SETQ VER1 (verticesurf na prov))
  )
  (command "" "")
  (COMMAND "-LAYER" "T" "*" "")
  (load (strcat ruta "extrim"))
  (command "change" na "" "P" "LA" LAYER "")
)

(defun verticeSURF (poli nov)
  (setq listap (entget poli))
  (setq nver 0)
  (setq salir "N")
  (while (= salir "N")
    (setq sublisp (car listap))
    (if (= 10 (car sublisp))
      (progn
        (setq punto (cdr sublisp))   
        (setq nver (+ nver 1))
      )
    )
    (setq listap (cdr listap))
    (if listap
      (setq salir "N")
      (setq salir "S")
    )
    (if (= nov nver)
      (setq salir "S")
    )
  )
  (if (not listap)
    (setq punto nil)
  )
  (setq punto punto)
)
