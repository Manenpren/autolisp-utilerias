(defun c:is3 ()
    (command "view" "s" "c" "y")
    (setq texto (car (entsel "Selecciona texto de cadenamiento: ")))
    (setq NOMBRE (cdr (assoc 1 (entget TEXTO))))
    (setq elev (car (entsel "Selecciona el texto de elevacion : ")))
    (setq n2 (cdr (assoc 1 (entget elev))))
    (setq texto2 (car (entsel "Selecciona texto proyecto: ")))
    (setq NOMBRE2 (cdr (assoc 1 (entget TEXTO2))))
    (setq xy (strcat "0, " n2))
    (command "insert" NOMBRE "0,0" "" "" "")
    (command "insert" nombre2 xy "" "" "")
    (command "CHANGE" TEXTO elev texto2 "" "P" "CO" "1" "")
    (COMMAND "ZOOM" "C" XY "15")
)
