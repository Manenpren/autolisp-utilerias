(defun C:ISS ()
  (C:LIBRERIA "BUSCA VALOR DE ATRIBUTO")
  (C:LIBRERIA "AREA OBTENIDA EN UN PUNTO")
  (COMMAND "UNDO" "M")
  (COMMAND "VIEW" "S" "C")
  (setq PROV (CAR (ENTSEL "SELECCIONA BLOCK")))
  (setq NOMBLO (cdr (assoc 2 (entget PROV))))
  (setq nb2 nomblo)
  (COMMAND "INSERT" NOMBLO "0,0" "" "" "")
  (SETQ X (ENTLAST))
  (COMMAND "EXPLODE" X "")
  (SETQ GPOA (SSGET "P"))
  (SETQ PROV (SSNAME GPOA 0))
  (SETQ P 1)
;  (SETQ GPODEL (SSADD))
  (WHILE (/= (cdr (assoc 0 (entget PROV))) "INSERT")
;    (IF (AND (= (cdr (assoc 8 (entget PROV))) "PROYECTO") (/= (cdr (assoc 0 (entget PROV))) "INSERT"))
;      (SSADD PROV GPODEL)
;    )
    (SETQ PROV (SSNAME GPOA P))
    (SETQ P (1+ P))
  )
  (setq XY (cdr (assoc 10 (entget PROV))))
  (COMMAND "ZOOM" "C" XY "20")
;  (COMMAND "SCALE" PROV "" XY "0.5")
;  (COMMAND "MOVE" PROV "" XY PAUSE)
;  (setq texto (car (entsel "Selecciona el texto DE TN: ")))
;  (setq cadena (cdr (assoc 1 (entget texto))))
;  (IF (/= (SUBSTR CADENA 1 1) "T")    
;    (SETQ CADENA (STRCAT "TN +" CADENA))
;  )
;   (COMMAND "CHANGE" texto "" "" "" "" "" "" CADENA)
  
;  (c:1)
;  (exit)

;  (WHILE PROV
;    (IF (AND (= (cdr (assoc 8 (entget PROV))) "PROYECTO") (/= (cdr (assoc 0 (entget PROV))) "INSERT"))
;      (SSADD PROV GPODEL)
;    )
;    (SETQ PROV (SSNAME GPOA P))
;    (SETQ P (1+ P))
;  )
;    (setq nombre nomblo)
;    (SETQ LNG (STRLEN NOMBRE))
;    (SETQ NOMBLO "")
;    (SETQ CONT 0)
;    (REPEAT LNG
;        (SETQ CONT (1+ CONT))
;        (setq CARACTER (substr NOMBRE CONT 1))
;        (IF (= CARACTER "-") (SETQ CARACTER "+"))
;        (setq nomblo (STRCAT NOMBLO CARACTER))
;    )
;  (PROMPT "SELECCIONA LOS OBJETOS A BORRAR")
;  (COMMAND "ERASE" GPODEL "")
;  (SETQ PROYG (SSGET))
;  (COMMAND "ERASE" PROYG "")
;  (setq nomblo (strcat nomblo "P"))
;  (COMMAND "INSERT" NOMBLO "0,0" "" "" "")
;  (SETQ X (ENTLAST))
;  (COMMAND "EXPLODE" X "")
;  (SETQ GPOA2 (SSGET "P"))
  (SETQ ELEVPRV (BUSATR PROV "RASANTE"))
  (SETQ XY (STRCAT "0," ELEVPRV))
  (SETQ ELEVPRV (ATOF ELEVPRV))
  (COMMAND "ZOOM" "C" XY "20")
  (SETQ XYZ (STRCAT "0," (RTOS (- ELEVPRV 0.025) 2 3)))
  (SETQ XYZ2 (STRCAT "0," (RTOS (- ELEVPRV 0.15) 2 3)))
  (SETQ XYZ3 (STRCAT "0," (RTOS (- ELEVPRV 0.35) 2 3)))
  (COMMAND "LAYER" "F" "*" "")
  (SETQ ACA (AREAP XYZ ARP))
  (SETQ ABH (AREAP XYZ2 ARP))
  (SETQ ASR (AREAP XYZ3 ARP))
  (COMMAND "LAYER" "T" "*" "")
 ; (command "INSERT" (strcat ruta "BLOCKS\\AREASCHON.dwg") PAUSE "" "" "" "" "" "" "" "" "" "" "" "" "" "" "" "" "" "" "" "" "" "" "" "" "" "")
 ; (SSADD (ENTLAST) GPOBLK)
 ; (setq bl (entnext (ENTLAST)))
  (SETQ BL PROV)
  (setq bl (entnext BL))
;  (COMMAND "attedit" "" "" "" "" bl "V" "R" CADENAMIENTO "")
  (setq bl (entnext BL))
;  (COMMAND "attedit" "" "" "" "" bl "V" "R" ELEVPRV "")
  (setq bl (entnext BL))
  (setq bl (entnext BL))
  (setq bl (entnext BL))
  (setq bl (entnext BL))
  (setq bl (entnext BL))
  (setq bl (entnext BL))
  (COMMAND "attedit" "" "" "" "" bl "V" "R" ASR "")
  (setq bl (entnext BL))
  (COMMAND "attedit" "" "" "" "" bl "V" "R" ABH "")
  (setq bl (entnext BL))
  (COMMAND "attedit" "" "" "" "" bl "V" "R" ACA "")

  (COMMAND "BLOCK" Nb2 "Y" "0,0" GPOA "R" GPODEL "")
;  (COMMAND "ERASE" GPODEL "")
  (COMMAND "VIEW" "R" "C")
;  (C:2)
)

(DEFUN C:FIN ()
    (C:DY)
    (C:2)
    (setq T1 (CAR (ENTSEL "SELECCIONA TEXTO IGUAL")))
    (setq T2 (CAR (ENTSEL "SELECCIONA TEXTO IGUAL")))
    (COMMAND "SCALE" TEXTO "" (cdr (assoc 10 (entget TEXTO))) 2)
    (COMMAND "SCALE" T1 "" (cdr (assoc 10 (entget T1))) 0.8)
    (COMMAND "SCALE" T2 "" (cdr (assoc 10 (entget T2))) 0.8)
    (COMMAND "CHANGE" T1 "" "P" "LA" "TN" "")
    (COMMAND "CHANGE" T2 "" "P" "LA" "0" "")
    (C:MB)
    (COMMAND "VIEW" "R" "C")
)
