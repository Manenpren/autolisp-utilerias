(DEFUN C:EXRAN ()
  (command "undo" "m")
  (COMMAND "VIEW" "S" "PROV")
  (C:LIBRERIA "VERTICES DE UNA LWPOLYLINE")
  (C:LIBRERIA "BUSCA VALOR DE ATRIBUTO")
  (C:LIBRERIA "nombre carta topografica")
  (C:LIBRERIA "UTM-GEO")
  (C:LIBRERIA "CENTROIDE DE UN POLIGONO IRREGULAR")
  (C:LIBRERIA "BUSCA CLAVE DE LOCALIDAD")
  (C:LIBRERIA "BUSCA CLAVE DE MUNICIPIO")
  (C:LIBRERIA "BUSCA CLAVE DEL EJIDO")
  (SETQ OPCIONESOS (GETVAR "OSMODE"))
  (command "osnap" "none")
  (IF (= NOMMUN NIL) (SETQ NOMMUN "X"))
  (SETQ NOMMUN1 (STRCASE (GETSTRING PROMPT (STRCAT "\n NOMBRE DEL MUNICIPIO <" NOMMUN ">:"))))
  (IF (/= NOMMUN1 "")
    (SETQ NOMMUN NOMMUN1)
  )
  (setq clmun (CLAVEMUNI NOMMUN))
  (IF (= (STRLEN CLMUN) 1) (SETQ CLMUN (STRCAT "00" CLMUN)))
  (IF (= (STRLEN CLMUN) 2) (SETQ CLMUN (STRCAT "0" CLMUN)))
  (IF (= CLMUN NIL) (SETQ CLMUN "XXX"))
  (SETQ CLMUN1 (GETSTRING (STRCAT "\n CLAVE DEL MUNICIPIO <" CLMUN ">:")))
  (IF (/= CLMUN1 "")
    (SETQ CLMUN CLMUN1)
  )
  (IF (= NOMEJI NIL) (SETQ NOMEJI "X"))
  (SETQ NOMEJI1 (STRCASE (GETSTRING PROMPT (STRCAT "\n NOMBRE DEL EJIDO <" NOMEJI ">:"))))
  (IF (/= NOMEJI1 "")
    (SETQ NOMEJI NOMEJI1)
  )
  (setq CLEJI (CLAVEJIDO nomEJI CLMUN))
  (IF (= (STRLEN CLEJI) 1) (SETQ CLEJI (STRCAT "00" CLEJI)))
  (IF (= (STRLEN CLEJI) 2) (SETQ CLEJI (STRCAT "0" CLEJI)))
  (IF (= CLEJI NIL) (SETQ CLEJI "XXX"))
  (SETQ CLEJI1 (GETSTRING (STRCAT "\n CLAVE DEL EJIDO <" CLEJI ">:")))
  (IF (/= CLEJI1 "")
    (SETQ CLEJI CLEJI1)
  )
  (IF (= NOMLOC NIL) (SETQ NOMLOC "X"))
  (SETQ NOMLOC1 (STRCASE (GETSTRING PROMPT (STRCAT "\n NOMBRE DE LA LOCALIDAD <" NOMLOC ">:"))))
  (IF (/= NOMLOC1 "")
    (SETQ NOMLOC NOMLOC1)
  )
  (setq clLOC (CLAVELOCALIDAD nomLOC CLMUN))
  (IF (= (STRLEN CLLOC) 1) (SETQ CLLOC (STRCAT "000" CLLOC)))
  (IF (= (STRLEN CLLOC) 2) (SETQ CLLOC (STRCAT "00" CLLOC)))
  (IF (= (STRLEN CLLOC) 3) (SETQ CLLOC (STRCAT "0" CLLOC)))
  (IF (= CLLOC NIL) (SETQ CLLOC "XXXX"))
  (SETQ CLLOC1 (GETSTRING (STRCAT "\n CLAVE DE LA LOCALIDAD <" CLLOC ">:")))
  (IF (/= CLLOC1 "")
    (SETQ CLLOC CLLOC1)
  )
  (if (= zonah nil) (setq zonah "00"))
  (SETQ zonah1 (GETSTRING (strcat "\n ZONA UTM HORARIA <" zonah ">:")))
  (IF (/= zonah1 "")
    (SETQ zonah zonah1)
  )
  (if (= npejid nil) (setq npejid "1"))
  (SETQ npejid2 (GETSTRING (strcat "\n NUMERO DE POLIGONO EJIDAL <" npejid ">:")))
  (IF (/= npejid2 "")
    (SETQ npejid npejid2)
  )
  (SETQ TPREDIO (GETSTRING "\n TIPO DE PREDIO :"))
  (PROMPT "SELECCIONA LOS POLIGONOS DEL EJIDO Y LA CLINICA ")
  (setq gpoCLINEJID (ssget))
  (SETQ EX1 (SSNAME gpoCLINEJID 0))
  (SETQ EX2 (SSNAME gpoCLINEJID 1))
  (COMMAND "AREA" "E" EX1)
  (SETQ SUPEX1 (RTOS (GETVAR "AREA") 2 3))
  (COMMAND "AREA" "E" EX2)
  (SETQ SUPEX2 (RTOS (GETVAR "AREA") 2 3))
  (IF (> (ATOF SUPEX1) (ATOF SUPEX2))
    (PROGN
      (SETQ ENTCLIN EX2)
      (SETQ SUPCLIN SUPEX2)
      (SETQ ENTEJI EX1)
      (SETQ SUPEJI SUPEX1)
    )
  )
  (IF (> (ATOF SUPEX2) (ATOF SUPEX1))
    (PROGN
      (SETQ ENTCLIN EX1)
      (SETQ SUPCLIN SUPEX1)
      (SETQ ENTEJI EX2)
      (SETQ SUPEJI SUPEX2)
    )
  )

  (setq xyz2 (cdr (centrpol entclin)))
  (setq xyz (cdr (centrpol enteji)))
  (PROMPT "SELECCIONA LAS LINEAS DE SEPARACION DE LINDERO")
  (setq gpoLINDL (ssget))
  (command "saveas" "dxf" "V" "2000" "o" "" (STRCAT "C:\\EXTRAE\\A" CLMUN "0" CLEJI ".DXF"))            ;ARCHIVO DE AFECTACIONES
  (setq ARCH (open (STRCAT "C:\\EXTRAE\\A" CLMUN "0" CLEJI ".TXT") "w"))
  (CLOSE ARCH)
  (setq NOMBRECARTA (CARTAING (UTM-GEO xyz (ATOI ZONAH))))
  (setq ARCH (open (STRCAT "C:\\EXTRAE\\C" CLMUN "0" CLEJI ".CE1") "w"))                 ;CEDULA DE INFORMACION DE VERTICES GEODESICOS
  (SETQ LINEA (STRCAT "16," (CHR 34) "MICHOACAN DE OCAMPO" (CHR 34) "," (itoa (ATOI CLMUN)) "," (CHR 34) NOMMUN (CHR 34) "," (itoa (ATOI CLEJI)) (CHR 34) NOMEJI (CHR 34) "," npejid "," (CHR 34) NOMBRECARTA (CHR 34) "," (CHR 34) "16000000" (CHR 34) "," (CHR 34) "181105" (CHR 34) ",19,58,39.5684,102,36,51.3224,749652.141,2210785.446," ZONAH "," (CHR 34) "0" (CHR 34) ",0,0"  "," (CHR 34) "0" (CHR 34) ",0,0" "," (CHR 34) "0" (CHR 34) ",0,0" "," (CHR 34) "0" (CHR 34) ",0,0" "," (CHR 34) "0" (CHR 34) ",0,0" "," (CHR 34) "0" (CHR 34) ",0,0"))
  (write-line LINEA arcH)
  (CLOSE ARCH)
  (setq ARCH (open (STRCAT "C:\\EXTRAE\\C" CLMUN "0" CLEJI ".CE2") "w"))                 ;CEDULA DE INFORMACION AL INTERIOR DEL EJIDO
  (SETQ LINEA (STRCAT "16," (CHR 34) "MICHOACAN DE OCAMPO" (CHR 34) "," (itoa (ATOI CLMUN)) "," (CHR 34) NOMMUN (CHR 34) "," (itoa (ATOI CLEJI)) "," (CHR 34) NOMEJI (CHR 34) ",2," npejid "," (CHR 34) "A" (CHR 34) "," (CHR 34) NOMBRECARTA (CHR 34) ",0,0,0,1,1,0," "16," "MICHOACAN DE OCAMPO" "," (itoa (ATOI CLMUN)) "," NOMMUN ",0,0,0," SUPEJI ",0,0,0,0.000,0.000,0.000"))
  (write-line LINEA arcH)
  (CLOSE ARCH)
  (setq ARCH (open (STRCAT "C:\\EXTRAE\\C" CLMUN "0" CLEJI ".CE5") "w"))                 ;CEDULA DE INFORMACION PARCELARIA
;  (SETQ LINEA (STRCAT "16," CLMUN "," CLEJI ",01,06," zonah ",00000,nombre ejidatario,fechanac," supclin ",0.000,0.000,0.000,0.000,0.000,16," (CHR 34) "MICHOACAN DE OCAMPO" (CHR 34) "," CLMUN "," NOMMUN))
;  (write-line LINEA arcH)
  (CLOSE ARCH)
  (setq ARCH (open (STRCAT "C:\\EXTRAE\\C" CLMUN "0" CLEJI ".CE7") "w"))                 ;CEDULA DE INFORMACION DE SOLARES URBANOS
  (SETQ LINEA (STRCAT "16," (itoa (ATOI CLMUN)) "," (itoa (ATOI CLEJI)) "," npejid "," (CHR 34) "J" (CHR 34) "," (CHR 34) "2" (CHR 34) "," (itoa (ATOI clloc)) "," (CHR 34) nomloc (CHR 34) ",1,1," (CHR 34) "CLINICA IMSS" (CHR 34) "," (CHR 34) (CHR 34) "," supclin ",0.000,0.000,0.000,0.000,0.000,0.000,0," (CHR 34) (CHR 34) ",0," (CHR 34) (CHR 34)))
  (write-line LINEA arcH)
  (CLOSE ARCH)
  (SETQ GPOCOL (SSADD))
  (SETQ VERTX (vertice ENTEJI 1))
  (SETQ CONT1 2)
  (WHILE VERTX
    (SETQ VERT2 VERTX)
    (SETQ VERTX (vertice ENTEJI CONT1))
    (SETQ CONT1 (1+ CONT1))
    (IF (/= VERTX NIL)
      (PROGN
        (setq pun1 VERTX) 
        (setq pun2 VERT2) 
        (setq x1 (car pun1))
        (setq y1 (car (cdr pun1)))
        (setq x2 (car pun2))
        (setq y2 (car (cdr pun2)))
        (setq xd (- x1 x2))
        (if (> 0 xd)
          (setq xd (* xd -1))
        )
        (setq xd (/ xd 2))
        (setq yd (- y1 y2))
        (if (> 0 yd)
          (setq yd (* yd -1))
        )
        (setq yd (/ yd 2))
        (if (> x1 x2)
          (setq xd (+ xd x2))
          (setq xd (+ xd x1))
        )
        (if (> y1 y2)
          (setq yd (+ yd y2))
          (setq yd (+ yd y1))
        )
        (setq punmid (list xd yd 0))  
        (SETQ CONTX (- CONT1 2))
        (SETQ XYZX (CONS 10 PUNMID))
        (SETQ TEXTX (CONS 1 (ITOA CONTX)))
        (ENTMAKE (LIST '(0 . "TEXT") '(100 . "AcDbEntity") '(8 . "0") '(100 . "AcDbText") XYZX '(40 . 1) TEXTX))
        (SSADD (ENTLAST) GPOCOL)
      )
    )
  );WHILE
  (SETQ GPOCOL2 (SSADD))
  (SETQ EX (SSNAME GPOLINDL 0))
  (SETQ CONT1 1)
  (WHILE EX
    (SETQ PUN1 (vertice EX 1))
    (SETQ PUN2 (vertice EX 2))
    (setq x1 (car pun1))
    (setq y1 (car (cdr pun1)))
    (setq x2 (car pun2))
    (setq y2 (car (cdr pun2)))
    (setq xd (- x1 x2))
    (if (> 0 xd)
      (setq xd (* xd -1))
    )
    (setq xd (/ xd 2))
    (setq yd (- y1 y2))
    (if (> 0 yd)
      (setq yd (* yd -1))
    )
    (setq yd (/ yd 2))
    (if (> x1 x2)
      (setq xd (+ xd x2))
      (setq xd (+ xd x1))
    )
    (if (> y1 y2)
      (setq yd (+ yd y2))
      (setq yd (+ yd y1))
    )
    (setq punmid (list xd yd 0))  
    (SETQ XYZX (CONS 10 PUNMID))
    (SETQ TEXTX (CONS 1 (ITOA CONTX)))
    (ENTMAKE (LIST '(0 . "TEXT") '(100 . "AcDbEntity") '(8 . "0") '(100 . "AcDbText") XYZX '(40 . 1) '(1 . "0")))
    (SSADD (ENTLAST) GPOCOL2)
    (SETQ EX (SSNAME GPOLINDL CONT1))
    (SETQ CONT1 (1+ CONT1))
  )
  (command "saveas" "dxf" "v" "2000" "o" GPOCOL GPOCOL2 gpoLINDL ENTEJI "" "" (STRCAT "C:\\EXTRAE\\C" CLMUN "0" CLEJI ".DXF"))      ;ARCHIVOS DE COLINDANCIAS
  (setq ARCH (open (STRCAT "C:\\EXTRAE\\C" CLMUN "0" CLEJI ".TXT") "w"))
  (REPEAT (sslength GPOCOL2)
    (SETQ LINEA (STRCAT "0,"(CHR 34) (CHR 34)))
    (write-line LINEA arcH)
  )
  (CLOSE ARCH)
  (COMMAND "SHELL" (STRCAT "COPY D:\\FORMAT~1\\L1040011.DXF C:\\EXTRAE\\L" CLMUN "0" CLEJI ".DXF"))
  (setq ARCH (open (STRCAT "C:\\EXTRAE\\M" CLMUN "0" CLEJI ".TXT") "w"))
  (SETQ LINEA (STRCAT "Ing. Mario Fernández Arreygue"))
  (write-line LINEA arcH)
  (SETQ LINEA (STRCAT ""))
  (write-line LINEA arcH)
  (SETQ LINEA (STRCAT ""))
  (write-line LINEA arcH)
  (SETQ LINEA (STRCAT ""))
  (write-line LINEA arcH)
  (SETQ LINEA (STRCAT ""))
  (write-line LINEA arcH)
  (SETQ LINEA (STRCAT ""))
  (write-line LINEA arcH)
  (SETQ LINEA (STRCAT ""))
  (write-line LINEA arcH)
  (CLOSE ARCH)
  (SETQ GPOX (SSADD))
  (SETQ XYZX (CONS 10 XYZ))
  (SETQ TEXTX (CONS 1 (STRCAT "01" CLLOC ZONAH "00100001001")))
  (ENTMAKE (LIST '(0 . "TEXT") '(100 . "AcDbEntity") '(8 . "0") '(100 . "AcDbText") XYZX '(40 . 10) TEXTX))
  (SSADD (ENTLAST) GPOX)
  (SETQ XYZX (CONS 10 XYZ2))
  (SETQ TEXTX (CONS 1 (STRCAT "01" CLLOC ZONAH "00100001002")))
  (ENTMAKE (LIST '(0 . "TEXT") '(100 . "AcDbEntity") '(8 . "0") '(100 . "AcDbText") XYZX '(40 . 10) TEXTX))
  (SSADD (ENTLAST) GPOX)
  (command "saveas" "dxf" "v" "2000" "o" ENTCLIN ENTEJI GPOX "" ""(STRCAT "C:\\EXTRAE\\P" CLMUN "0" CLEJI ".DXF"))     ;ARCHIVOS DE POLIGONOS
  (setq ARCH (open (STRCAT "C:\\EXTRAE\\P" CLMUN "0" CLEJI ".TXT") "w"))
  (SETQ TXT (STRCAT (CHR 34) "01" CLLOC ZONAH "00100001001" (CHR 34) ",09," (CHR 34) "RESERVA DE CRECIMIENTO" (CHR 34) "," (CHR 34) "T" (CHR 34) "," (CHR 34) (CHR 34) ",0"))
  (write-line TXT arcH)
  (SETQ TXT (STRCAT (CHR 34) "01" CLLOC ZONAH "00100001002" (CHR 34) ",06," (CHR 34) "CLINICA IMSS" (CHR 34) "," (CHR 34) "S" (CHR 34) "," (CHR 34) (CHR 34) ",0"))
  (write-line TXT arcH)
  (CLOSE ARCH)
  (SETQ GPOBLEJI (SSADD))
  (SETQ VERTX (vertice ENTEJI 1))
  (SETQ CONT1 2)
  (WHILE VERTX
    (setq punver1 (suma VERTX -0.01 -0.01))
    (setq punver2 (suma VERTX 0.01 0.01))
    (command "ZOOM" "W" punver1 punver2)
    (setq GpoPun (ssget "C" punver1 punver2 '((2 . "PUNTO"))))
    (IF (= 0 (SSLENGTH GPOPUN)) (PROGN (ALERT "FALTA BLOCK EN VERTICE") (COMMAND "ZOOM" "C" VERTX "10")))
    (COMMAND "ZOOM" "P")
    (SSADD (SSNAME GPOPUN 0) GPOBLEJI)
    (SETQ VERTX (vertice ENTEJI CONT1))
    (SETQ CONT1 (1+ CONT1))
  );WHILE
  (PROMPT "SELECCIONA LOS vertices de la clinica")
  (setq gpoblcli (ssget '((2 . "PUNTO"))))
  (SETQ GPOVERTX (SSADD))
  (SETQ EX (SSNAME GPOBLEJI 0))
  (SETQ CONT1 1)
  (setq ARCH (open (STRCAT "C:\\EXTRAE\\S" CLMUN "0" CLEJI ".TXT") "w"))
  (WHILE EX
    (setq XYZX (ASSOC 10 (ENTGET EX)))  
    (setq NPTO (busatr EX "PUNTO"))  
    (SETQ CADENAX (STRCAT (NTOS (ATOI NPTO)) "2900"))
    (SETQ TEXTX (CONS 1 CADENAX))
    (ENTMAKE (LIST '(0 . "TEXT") '(100 . "AcDbEntity") '(8 . "0") '(100 . "AcDbText") XYZX '(40 . 5) TEXTX))
    (SSADD (ENTLAST) GPOVERTX)
    (ENTMAKE (LIST '(0 . "POINT") '(8 . "0") XYZX))
    (SSADD (ENTLAST) GPOVERTX)
    (SETQ EX (SSNAME GPOBLEJI CONT1))
    (SETQ CONT1 (1+ CONT1))
    (SETQ LINEA (STRCAT CADENAX "," (CHR 34) (CHR 34)))
    (write-line LINEA arcH)
  )
  (SETQ EX (SSNAME GPOBLCLI 0))
  (SETQ CONT1 1)
  (WHILE EX
    (setq XYZX (ASSOC 10 (ENTGET EX)))  
    (setq NPTO (busatr EX "PUNTO"))  
    (SETQ CADENAX (STRCAT (NTOS (ATOI NPTO)) "3900"))
    (SETQ TEXTX (CONS 1 CADENAX))
    (ENTMAKE (LIST '(0 . "TEXT") '(100 . "AcDbEntity") '(8 . "0") '(100 . "AcDbText") XYZX '(40 . 5) TEXTX))
    (SSADD (ENTLAST) GPOVERTX)
    (ENTMAKE (LIST '(0 . "POINT") '(8 . "0") XYZX))
    (SSADD (ENTLAST) GPOVERTX)
    (SETQ EX (SSNAME GPOBLCLI CONT1))
    (SETQ CONT1 (1+ CONT1))
    (SETQ LINEA (STRCAT CADENAX "," (CHR 34) "clinica del imss" (CHR 34)))
    (write-line LINEA arcH)
  )
  (CLOSE ARCH)
  (command "saveas" "dxf" "v" "2000" "o" GPOVERTX "" "" (STRCAT "C:\\EXTRAE\\S" CLMUN "0" CLEJI ".DXF"))
)

(DEFUN NTOS (NUM)
  (SETQ F (STRLEN (ITOA NUM)))
  (SETQ FS (ITOA NUM))
  (REPEAT (- 5 F)
    (SETQ FS (STRCAT "0" FS))
  )
  (SETQ NUM FS)
)

(defun v1 ()
  (setq res "A")
  (done_dialog)
)

(defun v2 ()
  (setq res "P")
  (done_dialog)
)

(defun leevar ()
  (setq nomblo (get_tile "Nblock"))
  (done_dialog)
)

(defun CEROS (cadintercambio)
  (SETQ CADENAFINAL cadintercambio)
  (SETQ CONTDD 0)
  (REPEAT 10
    (setq cadenafinal (vl-string-subst (strcat "/0" (itoa contdd) "/") (strcat "/" (itoa contdd) "/") cadenafinal))
    (setq cadenafinal (vl-string-subst (strcat "/0" (itoa contdd) ".") (strcat "/" (itoa contdd) ".") cadenafinal))
    (setq contdd (1+ contdd))
  )
  (SETQ cadintercambio CADENAFINAL)
)

(defun qcomas (cadintercambio)
  (SETQ CARX (SUBSTR cadintercambio 1 1))
  (setq contadorx 1)
  (setq cadenadesalida "")
  (while (/= carx "")
    (SETQ CARX (SUBSTR cadintercambio contadorx 1))
    (if (/= carx ",") (setq cadenadesalida (strcat cadenadesalida carx)))
    (setq contadorx (1+ contadorx))
  )
  (setq cadenadesalida cadenadesalida)
)
(DEFUN SUMA (P VX VY)
  (SETQ XSUMA (CAR P))
  (SETQ YSUMA (CAR (CDR P)))
  (LIST (+ XSUMA VX) (+ YSUMA VY) (LAST P))
)

(DEFUN MPUNex (POLI)
  (C:LIBRERIA "SEPARA VALORES DE COMAS DE UN TEXTO TO LISTA")
  (SETQ TIPOPLANO (GETSTRING "\n TIPO DE PLANO? ('A'sentamientos/'U'so comun/'I'nterno/'P'arcela/'S'olar):"))
  (if (= (strcase tipoplano) "S")
    (progn
     (setq lescalas "100,200,500,1000,1500")
     (SETQ lescalas2 (SEPARA_VAL_COMAS lescalas))
    )
  )
  (if (= (strcase tipoplano) "P")
    (progn
     (setq lescalas "200,500,1000,2500,5000,10000,20000,50000,75000,100000")
     (SETQ lescalas2 (SEPARA_VAL_COMAS lescalas))
    )
  )
  (if (= (strcase tipoplano) "I")
    (progn
     (setq lescalas "1000,2500,5000,10000,20000,40000,50000,100000,125000,150000,175000,200000")
     (SETQ lescalas2 (SEPARA_VAL_COMAS lescalas))
    )
  )
  (if (= (strcase tipoplano) "U")
    (progn
     (setq lescalas "500,1000,2500,5000,10000,20000,50000,100000,125000,150000,175000,200000")
     (SETQ lescalas2 (SEPARA_VAL_COMAS lescalas))
    )
  )
  (if (= (strcase tipoplano) "A")
    (progn
     (setq lescalas "500,1000,2500,5000")
     (SETQ lescalas2 (SEPARA_VAL_COMAS lescalas))
    )
  )
  (setq poli (car (entsel "\n Selecciona la poligonal envolvente: ")))
  (SETQ PROV 1)
  (SETQ P1T (VERTICE POLI PROV))
  (SETQ XMENOR (CAR P1T))
  (SETQ YMENOR (CADR P1T))
  (SETQ XMAYOR XMENOR)
  (SETQ YMAYOR YMENOR)
  (SETQ PROVV P1T)
  (while p1t
    (SETQ X2PROV (CAR P1T))
    (SETQ Y2PROV (CADR P1T))
    (IF (AND (< X2PROV XMENOR) (/= X2PROV nil)) (SETQ XMENOR X2PROV))
    (IF (AND (< Y2PROV YMENOR) (/= Y2PROV nil)) (SETQ YMENOR Y2PROV))
    (IF (AND (> X2PROV XMAYOR) (/= X2PROV nil)) (SETQ XMAYOR X2PROV))
    (IF (AND (> Y2PROV YMAYOR) (/= Y2PROV nil)) (SETQ YMAYOR Y2PROV))
    (SETQ PROV (1+ PROV))
    (SETQ P1T (VERTICE POLI PROV))
  )
  (setq dosx (* (- xmayor xmenor) 0.30))
  (setq dosy (* (- ymayor ymenor) 0.30))
  (COMMAND "ZOOM" "W" (STRCAT (RTOS (- XMENOR dosx) 2 6) "," (RTOS (- YMENOR dosy) 2 6)) (STRCAT (RTOS (+ XMAYOR dosx) 2 6) "," (RTOS (+ YMAYOR dosy) 2 6))) 
  (REDRAW POLI 3)
  (if (< (/ (- ymayor ymenor) (- xmayor xmenor)) 0.92857)
    (PROGN
      (setq dsten (- xmayor xmenor))
      (setq escalal (cdr (assoc 1 lescalas2)))
      (setq cont 2)
      (while escalal
        (setq comprob (fix (/ dsten (* 0.84 escalal))))
        (if (/= comprob 1) 
          (progn 
            (setq escalal (cdr (assoc cont lescalas2)))
            (setq cont (1+ cont))
          )
        )
        (if (= comprob 1) 
          (setq escalal NIL)
        )
      )
    )
    (PROGN
      (setq dsten (- ymayor ymenor))
      (setq escalal (cdr (assoc 1 lescalas2)))
      (setq cont 2)
      (while escalal
        (setq comprob (fix (/ dsten (* 0.78 escalal))))
        (if (/= comprob 1) 
          (progn 
            (setq escalal (cdr (assoc cont lescalas2)))
            (setq cont (1+ cont))
          )
        )
        (if (= comprob 1) 
          (setq escalal NIL)
        )
      )
    )
  )
  

  (SETQ PROV 1)
  (SETQ P1T (VERTICE POLI PROV))
  (WHILE P1T
    (setq gpoLP (ssget "C" (suma p1T 0.10 0.10) (suma p1T -0.10 -0.10)))
    (SETQ R (sslength gpoLP))
    (SETQ PROV2 0)
    (setq mdist 100)
    (SETQ OBCOR NIL)
    (REPEAT R
      (SETQ OBJP (ssname gpoLP PROV2))
      (if (= "PUNTO" (cdr (assoc 2 (entget OBJP))))
       (progn
        (SETQ PVT (cdr (assoc 10 (entget OBJP))))
        (setq pdist (distance p1T pvT))
        (if (> mdist pdist)
         (progn
          (setq mdist pdist)
          (setq obcor objP)
         )
        )
       )
      )
      (SETQ PROV2 (1+ PROV2))
    )
    (if (AND (< 0 MDIST) (/= obcor nil))
    (if (= noterr "1")
     (IF (> MDIST 0.01)
      (PROGN
       (ALERT "HAY UN BLOCK FUERA DE SU POSICION")
       (SETQ XYZ (cdr (assoc 10 (ENTGET OBCOR))))
       (COMMAND "ZOOM" "C" XYZ "4")
       (COMMAND "CIRCLE" XYZ ".1")
       (SETQ PROVE (ENTLAST))
       (setQ OPT (GETSTRING "DESEAS MOVERLO HACIA LA LINEA (S/N) <S> :"))
       (IF (= "CIRCLE" (cdr (assoc 0 (ENTGET PROVE))))
         (COMMAND "ERASE" PROVE "")
       )
       (IF (= OPT "")
          (SETQ OPT "S") 
       )
       (IF (= OPT "S")
        (PROGN
         (command "MOVE" OBCOR "" (cdr (assoc 10 (entget OBCOR))) P1T)
        )
       )
       (COMMAND "ZOOM" "P")
      )
     )
      (if (= oppdesf "1")
        (command "MOVE" OBCOR "" (cdr (assoc 10 (entget OBCOR))) P1T)
      )
     )
    )
    (SETQ PROV (1+ PROV))
    (SETQ P1T (VERTICE POLI PROV))
    (IF (AND (/= P1T NIL) (/= PROVV NIL))
     (PROGN
      (setq pRdist (distance p1T PROVV))
      (IF (= PRDIST 0)
       (PROGN
        (ALERT "TIENES UNA DISTANCIA 'CERO' EN DOS VERTICES DISTINTOS")
        (command "ZOOM" "C" P1T 10)
        (COMMAND "CIRCLE" P1T "5")
        (FINISH)
       )
      )
      (SETQ PROVV P1T)
     )
    )
  )         
)

(defun verticeSURF (poli nov)
  (setq listap (entget poli))
  (setq nver 0)
  (setq salir "N")
  (while (= salir "N")
    (setq sublisp (car listap))
    (if (= 10 (car sublisp))
      (progn
        (setq punto (cdr sublisp))   
        (setq nver (+ nver 1))
      )
    )
    (setq listap (cdr listap))
    (if listap
      (setq salir "N")
      (setq salir "S")
    )
    (if (= nov nver)
      (setq salir "S")
    )
  )
  (if (not listap)
    (setq punto nil)
  )
  (setq punto punto)
)
