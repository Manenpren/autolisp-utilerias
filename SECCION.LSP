(defun suma (punto xx yy)
  (setq xxx (car punto))
  (setq yyy (car (cdr punto)))
  (setq xxx (+ xxx xx))
  (setq yyy (+ yyy yy))
  (list xxx yyy)
)

(defun asigna ()
  (setq xm (car (cdr (assoc 10 (entget ob)))))
  (setq xml ele2)
)

(defun redo5 (daton)
  (setq daton (rtos daton 2 3))
  (setq cara (substr daton 1 1))
  (setq cuecar 1)
  (setq encpun 0)
  (setq pospun 0)
  (while (/= cara "")
    (setq cara (substr daton cuecar 1))
    (if (= cara ".")
      (progn
        (setq encpun 1)
        (setq pospun cuecar)
      )
    )
    (setq cuecar (+ cuecar 1))
  )    
  (if (= encpun 1)
    (progn
      (if (= (strlen daton) 1)            
        (setq daton daton)
      )
      (setq numdec (strlen (substr daton pospun)))
      (setq daton (substr daton 1 (- (strlen daton) numdec)))
    )
    (setq daton daton)
  )

;  (setq ultimo (atof (substr daton (strlen daton) 1)))
;  (if (/= ultimo 0)
;    (progn
;      (setq inicio (substr daton 1 (- (strlen daton) 1)))
;      (if (> 6 ultimo)
;        (setq daton (atof (strcat inicio "5")))
;        (setq daton (+ (atof (strcat inicio "0")) 10))
;      )
;    )
;    (setq daton (atof daton))
;  )
  (setq daton (atof daton))
)


(defun ordenax ()
  (setq ele2 0)
  (setq xlm 0)
  (setq ob (ssname gpo ele2))
  (setq xm (car (cdr (assoc 10 (entget ob)))))  
  (while ob
    (if (>= (car (cdr (assoc 10 (entget ob)))) xm)
      (asigna)
    )
    (setq ele2 (+ ele2 1))
    (setq ob (ssname gpo ele2))
  )
)

(defun cadena ()
  (setq cad ob)
  (setq cadtex (cdr (assoc 1 (entget cad))))
  (setq numtxt ele)
)

(defun ordena ()
  (setq ele 0)
  (setq ob (ssname gpo ele))
  (while ob
    (if (= "LINE" (cdr (assoc 0 (entget ob))))
      (setq numli ele)
    )
    (if (= "TEXT" (cdr (assoc 0 (entget ob))))
      (cadena)
    )
    (setq ele (+ ele 1))
    (setq ob (ssname gpo ele))
  )
  (setq gpoo (ssadd (ssname gpo numtxt)))
  (setq gpoo (ssadd (ssname gpo numli)))
  (ssdel (ssname gpo numli) gpo)
  (if (> numtxt numli)
    (setq numtxt (- numtxt 1))
  )
  (ssdel (ssname gpo numtxt) gpo)

  (setq ele 0)
  (setq ele2 0)
  (setq ob (ssname gpo ele))
  (while (/= ele (- eleme 2))
    (ordenax)
    (ssadd (ssname gpo xml) gpoo)
    (ssdel (ssname gpo xml) gpo)
    (setq ele (+ ele 1))
  )
)

(defun ordena2 ()
  (setq ele 0)
  (setq ob (ssname gpo ele))
  (while ob
    (if (= "LINE" (cdr (assoc 0 (entget ob))))
      (setq numli ele)
    )
    (setq ele (+ ele 1))
    (setq ob (ssname gpo ele))
  )
  (setq gpoo (ssadd (ssname gpo numli)))
  (ssdel (ssname gpo numli) gpo)

  (setq ele 0)
  (setq ele2 0)
  (setq ob (ssname gpo ele))
  (while (/= ele (- eleme 1))
    (ordenax)
    (ssadd (ssname gpo xml) gpoo)
    (ssdel (ssname gpo xml) gpo)
    (setq ele (+ ele 1))
  )
)


(defun ver1 ()
  (setq ele 0)
  (setq ob (ssname gpoo ele))
  (while ob
    (prin1 (entget ob))
    (write-line " ")
    (setq ele (+ ele 1))
    (setq ob (ssname gpoo ele))
  )
)

(defun ver2 ()
  (setq ele 0)
  (setq ob (ssname gpo ele))
  (while ob
    (prin1 (entget ob))
    (write-line " ")
    (setq ele (+ ele 1))
    (setq ob (ssname gpo ele))
  )
)

(defun mueve ()
  (setq p11 (suma (cdr (assoc 10 (entget (ssname gpoo 0)))) 0.1 0.1))
  (setq p12 (suma (cdr (assoc 10 (entget (ssname gpoo 0)))) -0.1 -0.1))
  (command "ZOOM" "w" p11 p12)
;  (SETQ GPO (ENTGET CAD))
;  (PRINT GPO)
;  (SETQ XOB1 (CDR (assoc 10 (entget (ssname GPO 0)))))
;  (SETQ XOB2 (CDR (assoc 10 (entget (ssname GPO (sslength GPO))))))
;  (SETQ PX1 (CAR XOB1))
;  (SETQ PY1 (CADR XOB1))
;  (SETQ PX2 (CAR XOB2))
;  (SETQ PY2 (CADR XOB2))
;  (IF (= PX1 PX2)
;    (SETQ MX PX1)
;    (SETQ MX (/ (ABS (- PX1 PX2)) 2))
;  )
;  (IF (= PY1 PY2)
;    (SETQ MY PY1)
;    (SETQ MY (/ (ABS (- PY1 PY2)) 2))
;  )
;  (IF (> PX1 PX2)
;    (SETQ MX (+ PX2 MX))
;    (SETQ MX (+ PX1 MX))
;  )
;  (IF (> PY1 PY2)
;    (SETQ MY (+ PY2 MY))
;    (SETQ MY (+ PY1 MY))
;  )
;  (SETQ MY (RTOS MY 2 6))
;  (SETQ MX (RTOS MX 2 6))
;  (SETQ MITAD (STRCAT MX "," MY))
;  (command "MOVE" gpoo cad "" MITAD "0,0")
  (command "MOVE" gpoo cad "" "MID" (cdr (assoc 10 (entget (ssname gpoo 0)))) "0,0")
  (command "ZOOM" "w" "150,150" "-150,-150")
)

(defun rota ()
  (setq p1 (cdr (assoc 10 (entget (ssname gpoo 0)))))
  (setq p2 (cdr (assoc 11 (entget (ssname gpoo 0)))))
  (setq angulo (- 360.0 (atof (angtos (angle p1 p2) 0 4))))
  (command "ROTATE" gpoo cad "" "0,0" angulo)
  (setq r1 (getstring "\n Rotar 180 <N>:"))
  (if (= (strcase r1) "S")
    (command "ROTATE" gpoo cad "" "0,0" "180")
  )
)

(defun ez (obje)
  (setq obje (entnext obje))
  (if (= "ELEV" (strcase (cdr (assoc 2 (entget obje)))))
    (setq eleva (cdr (assoc 1 (entget obje))))
  )
  (setq obje (entnext obje))
  (if (= "ELEV" (strcase (cdr (assoc 2 (entget obje)))))
    (setq eleva (cdr (assoc 1 (entget obje))))
  )
  (setq obje (entnext obje))
  (if (= "ELEV" (strcase (cdr (assoc 2 (entget obje)))))
    (setq eleva (cdr (assoc 1 (entget obje))))
  )
  (setq elev (atof eleva))
)

(defun traza ()
  (setq ele 1)
  (setq ob1 (ssname gpoo ele))
  (setq p1 (cdr (assoc 10 (entget ob1))))
  (setq zm (ez ob1))
  (setq zn (ez ob1))
  (setq ob2 ob1)
  (setq salir 1)
  (setq gpoo2 (ssadd))
  (command "LAYER" "M" "SECCION" "")
  (command "LAYER" "S" "SECCION" "")
  (while salir
    (setq ele (+ ele 1))
    (setq ob2 (ssname gpoo ele))
    (setq p2 (cdr (assoc 10 (entget ob2))))
    (setq x1 (car p1))
    (setq x2 (car p2))
    (setq z1 (ez ob1))
    (setq z (ez ob2))
    (if (> z zm)
      (setq zm z)
    )
    (if (< z zn)
      (setq zn z)
    )
    (setq z2 (ez ob2))
    (setq p1r (list x1 z1))
    (setq p2r (list x2 z2))
    (command "LINE" p1r p2r "")
    (ssadd (entlast) gpoo2)
    (setq p1 p2)
    (setq ob1 ob2)
    (setq salir (ssname gpoo (+ ele 1)))
  )
)


(defun inserta ()
  (setq cco (ssname gpoo 1))
  (setq cco (entnext cco)) (setq cco (entnext cco))
  (setq cco (cdr (assoc 1 (entget cco))))
  (setq cco (- (atof cco) 3.5))
  (setq cco2 (- cco 5))
  (setq cco3 (- cco 10))
  (command "LINE" (strcat "0," (rtos (- cco3 1000) 2 2)) "@5000<90" "")
  (setq linv (entlast))
  (setq pl1 (cdr (assoc 10 (entget linv))))
  (setq pl2 (cdr (assoc 11 (entget linv))))
  (setq lina (ssname gpoo2 0))
  (setq cuenta 0)
  (while (/= cuenta (sslength gpoo2))
    (setq pl3 (cdr (assoc 10 (entget lina))))
    (setq pl4 (cdr (assoc 11 (entget lina))))
    (setq nivel (inters pl1 pl2 pl3 pl4 T))
    (setq cuenta (+ cuenta 1))
    (setq lina (ssname gpoo2 cuenta))
    (if nivel
      (setq cuenta (sslength gpoo2))
    )
  )
  (setq ycco1 (+ cco 10)) (setq ycco2 (- cco 10))
  (command "ZOOM" "W" (strcat (rtos (+ ancho 20)) "," (rtos ycco1 2 2)) (strcat (rtos (* (+ ancho 20) -1)) "," (rtos ycco2 2 2)))
  (command "VIEW" "S" "S")
  (setq cco (strcat "0," (rtos cco 2 2)))
  (command "MOVE" gpoo cad "" "0,0" (strcat "0," (rtos cco2 2 2)))
  (command "INSERT" "texto1" nivel "" "" "")
  (command "EXPLODE" (entlast))
  (setq nivel2 (car (cdr nivel)))
  (setq nivv (entlast))
  (entdel linv)
  (entmod (subst (cons 1 (rtos nivel2 2 3)) (assoc 1 (entget nivv)) (entget nivv)))
  (command "INSERT" "texto2" nivel "" "" "")
  (command "EXPLODE" (entlast))
  (setq cadt (entlast))
  (entmod (subst (cons 1 cadtex) (assoc 1 (entget cadt)) (entget cadt)))
  (if (= (strlen cadtex) 5)
    (setq cadtexx (strcat (substr cadtex 1 1) (substr cadtex 3)))
  )
  (if (= (strlen cadtex) 6)
    (setq cadtexx (strcat (substr cadtex 1 2) (substr cadtex 4)))
  )

)

(defun reticula ()
  (setq ym (car (cdr (assoc 10 (entget (ssname gpoo2 0))))))
  (setq yn (car (cdr (assoc 11 (entget (ssname gpoo2 (- (sslength gpoo2) 1)))))))
;  (setq ym1 (atof (rtos (+ ym 1) 2 0)))
;  (setq yn1 (atof (rtos (- yn 1) 2 0)))
  (setq ym1 ancho)
  (setq yn1 ancho)
  (setq zm1 (redo5 (+ zm 1)))
  (setq zn1 (redo5 (- zn 1)))
  (setq gporet (ssadd))
  (command "LAYER" "M" "RETICULA" "")
  (command "LAYER" "S" "RETICULA" "")
;  (command "LINE" (strcat "0," (rtos zn1)) (strcat "0," (rtos (- zm1 1))) "")
;  (ssadd (entlast) gporet)
;  (command "LINE" (strcat (rtos yn1) "," (rtos (+ zn1 1))) (strcat (rtos ym1) "," (rtos (+ zn1 1))) "")
;  (ssadd (entlast) gporet)
  (setq picad (list 0 (+ zn1 1)))
;  (command "INSERT" "texto2" picad "" "" "")
;  (command "EXPLODE" (entlast))
;  (setq cadt (entlast))
;  (entmod (subst (cons 1 cadtex) (assoc 1 (entget cadt)) (entget cadt)))
  (setq love (- zm1 zn1 2))
  (setq loho (- ym1 yn1 1))
  (setq cuenta 0)
  (setq cuetex septex)
  (setq znn1 zn1)
  (setq zn1 (+ zn1 1))
  (while (<= zn1 zm1)
    (if (= cuetex septex)
      (progn
        (command "INSERT" "RETH" (strcat (rtos (* ancho -1)) "," (rtos (+ zn1 0))) "" "" "")
        (command "EXPLODE" (entlast) "")
        (entmod (subst (cons 1 (rtos (+ zn1 0) 2 2)) (assoc 1 (entget (entlast))) (entget (entlast))))
        (ssadd (entlast) gporet)
        (command "INSERT" "RETH2" (strcat (rtos ancho) "," (rtos (+ zn1 0))) "" "" "")
        (command "EXPLODE" (entlast) "")
        (entmod (subst (cons 1 (rtos (+ zn1 0) 2 2)) (assoc 1 (entget (entlast))) (entget (entlast))))
        (ssadd (entlast) gporet)
        (setq cuetex 0)
      )
    )
    (command "LINE" (strcat (rtos ancho) "," (rtos (+ zn1 0))) (strcat (rtos (* ancho -1)) "," (rtos (+ zn1 0))) "")
    (ssadd (entlast) gporet)
    (setq zn1 (+ zn1 sepret))
    (setq cuetex (+ cuetex 1))
    (setq cuenta (+ cuenta 1))
  )
  (setq altosec (* (- cuenta 1) sepret))
  (setq cuenta 0)
  (setq yma (car (cdr (cdr (assoc 10 (entget (entlast)))))))
  (setq cuetex2 septex2)
  (setq yn1 (- yn1 1))
  (while (> (+ yn1 1) (* (+ sepret ancho) -1))
;    (setq cuenta (+ cuenta 1))
;    (if (/= yn1 -1)
;      (progn
        (if (= cuetex2 septex2)
          (progn
            (command "INSERT" "RETV" (strcat (rtos (+ yn1 1)) "," (rtos (+ znn1 1))) "" "" "")
            (command "EXPLODE" (entlast) "")
            (entmod (subst (cons 1 (rtos (+ yn1 1) 2 0)) (assoc 1 (entget (entlast))) (entget (entlast))))
            (ssadd (entlast) gporet)
            (setq cuetex2 0)
          )
        )
        (setq cuetex2 (+ cuetex2 1))
;      )
;    )
    (command "LINE" (strcat (rtos (+ yn1 1)) "," (rtos (+ znn1 1))) (strcat (rtos (+ yn1 1)) "," (rtos yma)) "")
    (ssadd (entlast) gporet)
    (setq yn1 (- yn1 sepret2))
  )
  (setq puninsblo (list yn1 zn1))
  (write-line (strcat (rtos nivel2 2 3) "," cadtexx "," (rtos altosec 2 2)) ArchS)
  (write-line (rtos altosec 2 2))
)


(defun bloque ()
  (command "ERASE" gpoo cad "")
    (SETQ LNG (STRLEN CADTEXT))
    (SETQ NOMBLO "")
    (SETQ CONT 0)
    (REPEAT LNG
        (SETQ CONT (1+ CONT))
        (setq CARACTER (substr CADTEXT CONT 1))
        (IF (= CARACTER "+") (SETQ CARACTER "-"))
        (setq nomblo (STRCAT NOMBLO CARACTER))
    )
;  (setq nomblo (strcat (substr cadtex 1 1) "-" (substr cadtex 3 3)))
  (command "BLOCK" nomblo puninsblo gpoo2 gporet cadt nivv "")
  (command "VIEW" "R" "C")
)

(defun borrar ()
  (setq r2 (getstring " Eliminar los datos en planta y crear bloque <S>:"))
  (if (= r2 "")
    (setq r2 "S")
  )
  (if (= (strcase r2) "S")
    (bloque)
  )
)

(defun c:se ()
  (command "OSNAP" "none")
  (if (not NomArcs)
    (progn
      (setq NomArcs (getstring " Nombre del archivo a anexarle datos: "))
    )
  )
  (setq ArchS (open (strcat "c:\\topograf\\" NomArcs) "a"))
  (if (not ancho)
    (setq ancho (getreal "Mitad del ancho de la seccion: "))
  )
  (if (not sepret)
    (setq sepret (getreal "Separacion de la reticula vertical: "))
  )
  (if (not sepret2)
    (setq sepret2 (getreal "Separacion de la reticula horizontal "))
  )
  (if (not septex)
    (setq septex (getint "Separacion de los textos verticales "))
  )
  (if (not septex2)
    (setq septex2 (getint "Separacion de los textos horizontales "))
  )
  (print "\n Seleciona los elementos a procesar ")
  (command "VIEW" "S" "C")
  (setq gpo (ssget))
  (setq eleme (sslength gpo))
  (setq gpoo (ssadd))
  (ordena)
  (mueve)
  (rota)
  (setq eleme (- eleme 1))
  (setq gpo gpoo)
  (ordena2)
  (traza)
  (ver1)
  (inserta)
  (reticula)
  (borrar)
  (close archs)
)

(defun c:RESE ()
  (setq ancho nil)
  (setq sepret nil)
  (setq sepret2 nil)
  (setq septex nil)
  (setq septex2 nil)
  (setq NomArcs nil)
  (write-line "Valores Reinicializados de secciones")
)

(defun cottopo (nume)
  (setq texto (rtos nume 2 0))
  (setq kilm 0)
  (if (= nume 0)
    (prin1 (setq resto "000"))
  )
  (if (> nume 9)
    (setq resto (strcat "0" texto))
  )
  (if (> nume 99)
   (setq resto texto)
  )
  (if (> nume 999)
    (progn
       (setq num1 (substr texto 1 1))
       (setq resto (substr texto 2 3))
    )
    (setq num1 "0")
  )
  (if (> nume 9999)
    (progn
      (setq num1 (substr texto 1 2))
      (setq resto (substr texto 3 3))
    )
  )
  (setq nuetex (strcat num1 "-" resto))
)

(defun DatC (linea nudato)
  (setq cuen 0)
  (setq cuecom 0)
  (setq salir "N")
  (setq cadena "")
  (while (/= salir "S")
    (setq cuen (+ cuen 1))
    (setq caracter (substr linea cuen 1))
    (if (= caracter ",")
      (setq cuecom (+ cuecom 1))
    )
    (if (= cuecom (- nudato 1))
      (if (/= caracter ",")
        (setq cadena (strcat cadena caracter))
      )
    )
    (if (or (= cuecom nudato) (>= cuen (strlen linea)))
      (setq salir "S")
    )
  )
  (setq cadena cadena)
)


(defun c:DESSEC ()
  (if (not NomArcs)
    (progn
      (setq NomArcs (getstring " Nombre del archivo a extraer alto de seccion: "))
    )
  )
  (setq ArchS (open (strcat "c:\\topograf\\" NomArcs) "r"))

  (setq inc (getint " Incremento: "))
  (setq sepsecf (getreal " Separación entre filas: "))

  (setq pun (getpoint " Punto de inicio de descarga: "))
  (setq ypuno (car (cdr pun)))
  (setq SecCol 0)
  (setq CueSec 1)
  (setq lin (read-line ArchS))
  (while lin
    (setq lin (read-line ArchS))
    (setq alto (atof (DatC lin 3)))
    (command "INSERT" (cottopo SecCol) pun "" "" "")
    (setq CueSec (+ CueSec 1))
    (setq SecCol (+ SecCol inc))
    (setq xpun (car pun))
    (setq ypun (car (cdr pun)))
    (setq ypun (+ ypun sepsecf alto))
;    (if (= CueSec (+ NumSec 1))
;      (progn
;        (setq xpun (+ xpun (* (+ ancho sepsecc) 2)))
;        (setq CueSec 1)
;        (setq ypun ypuno)
;      )
;    )
    (setq pun (list xpun ypun))
  )
)
