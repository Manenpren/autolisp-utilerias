(DEFUN C:LIMPI ()
  (IF (= LAYCONG NIL) (SETQ LAYCONG "GSLAYER"))
  (IF (/= VLIMPIA 1)
   (PROGN  
    (setq laycong "GSLAYER")
    (setq e (car (entsel "\nSelecciona la Polylinea : ")))
    (setq PE (getpoint "\nPunto exterior : "))
    (while (/= "LWPOLYLINE" (cdr (assoc 0 (entget E))))
        (if (/= "LWPOLYLINE" (cdr (assoc 0 (entget E))))
            (progn
              (alert "EL objeto seleccionado debe ser polylinea !")
              (setq E (car (entsel "\n Selecciona la Polylinea : ")))
            )
        )
    )
   )
  )
    (setq layer (cdr (assoc 8 (entget E))))
    (if (/= LAYCONG layer)
      (command "change" e "" "P" "LA" "GSLAYER" "")
    )
  (COMMAND "-LAYER" "SET" LAYCONG "FR" "*" "")
  (load (strcat ruta "exlimpia14"))
  (c:EXTRIM)
  (SETQ PROV 1)
  (COMMAND "ERASE" "ALL" "R" "CP")
  (Setvar "cmdecho" 1)
  (Setvar "highlight" 1)
  (Setvar "regenmode" 1)
  (Setvar "osmode" 0)
  (Setvar "ucsicon" 1)
  (Setvar "offsetdist" -1.0)
  (Setvar "attreq" 1)
  (Setvar "plinewid" 0.0)
  (Setvar "gridmode" 0)
  (Setvar "celtype" "BYLAYER")
  (WHILE VER1
     (SETQ VER1 (verticesurf e prov))
     (IF (/= VER1 NIL)
      (progn
        (SETQ Y (CADR ver1))
        (SETQ Y (RTOS Y 2 3))
        (SETQ X (CAR ver1))
        (SETQ X (RTOS X 2 3))
        (PRINT (STRCAT X "," Y))
        (COMMAND (STRCAT X "," Y))
      )
      (COMMAND "")
     )
     (SETQ PROV (1+ PROV))
  )
  (command "")
  (load (strcat ruta "extrim14"))
  (COMMAND "-LAYER" "T" "*" "")
)

(defun verticeSURF (poli nov)
  (setq listap (entget poli))
  (setq nver 0)
  (setq salir "N")
  (while (= salir "N")
    (setq sublisp (car listap))
    (if (= 10 (car sublisp))
      (progn
        (setq punto (cdr sublisp))   
        (setq nver (+ nver 1))
      )
    )
    (setq listap (cdr listap))
    (if listap
      (setq salir "N")
      (setq salir "S")
    )
    (if (= nov nver)
      (setq salir "S")
    )
  )
  (if (not listap)
    (setq punto nil)
  )
  (setq punto punto)
)
