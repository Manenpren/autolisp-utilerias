(defun c:une ()
;  (COMMAND "SHELL" "dir c:\topograf\taca\*.dwg > c:\dir.txt /o:n")
;  (setq ArcH (open "c:\\DIR.txt" "r"))
;  (setq ArcH2 (open "c:\\BD.txt" "w"))
;  (READ-LINE ARCH)
;  (READ-LINE ARCH)
;  (READ-LINE ARCH)
;  (READ-LINE ARCH)
;  (READ-LINE ARCH)
;  (SETQ LIN (READ-LINE ARCH))
;  (SETQ NARCH (SUBSTR LIN 1 8))
;  (WRITE-LINE NARCH ARCH2)
;  (WHILE LIN 
;    (SETQ LIN (READ-LINE ARCH))
;    (IF (= (SUBSTR LIN 1 1) " ")
;      (SETQ LIN NIL)
;    )
;    (IF (/= LIN NIL)
;      (PROGN
;        (SETQ NARCH (SUBSTR LIN 1 8))
;        (WRITE-LINE NARCH ARCH2)
;      )
;    )
;  )
;  (CLOSE ARCH)
;  (CLOSE ARCH2)
  (setq ArcH (open "c:\\BD.txt" "r"))
  (SETQ LIN (READ-LINE ARCH)) 
  (WHILE LIN 
    (IF (/= LIN NIL)
      (PROGN
        (COMMAND "INSERT" (STRCAT "D:\\CIUDADES\\HIDALGO\\CURVAS\\" LIN) "0,0" "" "" "")
;        (COMMAND "xref" "A" (STRCAT "C:\\fortin\\" LIN) "0,0" "" "" "")
;        (command "explode" "l" "")
;        (command "purge" "b" "" "" "y")
;        (COMMAND "ZOOM" "E")
;        (command "qsave")
        (COMMAND "DELAY" "200")
;        (COMMAND "SAVEAS" "" (STRCAT "C:\\ARJ\\mor1") "y")
;        (getstring "pulsa enter para insertar otro")
        (setq ArcH2 (open "c:\\$p.prv" "W"))
        (write-line lin arch2)
        (close arch2)
;        (COMMAND "ERASE" "ALL" "")
      )
    )
    (SETQ LIN (READ-LINE ARCH))
  )
  (CLOSE ARCH)
)
