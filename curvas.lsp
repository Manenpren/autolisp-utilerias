(defun c:curvas1 ()
  (C:LIBRERIA "BUSCA VALOR DE ATRIBUTO")
  (command "undo" "m")
  (setq dcl_id (load_dialog (strcat ruta "dialogos\\curvas.dcl"))) 
  (if (not (new_dialog "curv" dcl_id))   
    (exit)                                
                                          
  )
  (action_tile "arcsv" "(v1)")
  (action_tile "selec" "(v2)")
  (action_tile "cancel" "(exit)")
  (start_dialog)                          
  (princ)
  (if (= res "A")
    (setq NOMARCH (getfiled "Archivo con niveles" "*." "CSV" 18))
    (setq nomarch (strcat ruta "niv.csv"))
  )
  (setq arch (open (strcat ruta "ruta.prv") "w"))
  (write-line nomarch arch)
  (close arch)
  (if (= res "S")
    (progn
      (if (not (new_dialog "curv12" dcl_id))   
        (exit)                                
      )
      (action_tile "todos" "(v3)")
      (action_tile "grupo" "(v4)")
      (action_tile "cancel" "(exit)")
      (start_dialog)                          
      (princ)
      (if (= res2 "T")
        (SETQ GPONIV (ssget "X" '((0 . "INSERT") (2 . "PUN2"))))
        (SETQ GPONIV (ssget '((0 . "INSERT") (2 . "PUN2"))))
      )
      (setq e (ssname gponiv 0))
      (setq conta 1)
      (setq ArcDES (open (strcat ruta "niv.csv") "w"))
      (while e
        (SETQ LINEA "")
        (if (= (cdr (assoc 0 (entget E))) "INSERT")
          (PROGN
            (SETQ ELEVA (BUSATR E "ELEV"))
            (if (/= eleva nil)
             (progn
              (SETQ CODIG (BUSATR E "CODE"))
              (SETQ PUNTO (cdr (assoc 10 (entget E))))
              (SETQ X (CAR PUNTO))
              (SETQ X (RTOS X 2 5))
              (SETQ Y (CADR PUNTO))
              (SETQ Y (RTOS Y 2 5))
              (SETQ LINEA (STRCAT X "," Y "," ELEVA "," (ITOA CONTA)  "," CODIG))
             )
            )
          )
        )
        (IF (/= LINEA "")
           (WRITE-LINE LINEA ARCDES)
        )
        (setq e (ssname gponiv conta))
        (setq conta (1+ conta))
      )
      (CLOSE ARCDES)
    )
  )
  (if (not (new_dialog "curv2" dcl_id))   
    (exit)                                
                                          
  )
  (action_tile "polig" "(v5)")
  (action_tile "poligm" "(v6)")
  (action_tile "cancel" "(exit)")
  (start_dialog)                          
  (princ)
  (if (= RES3 "M")
    (progn 
      (setq pto (getpoint "\n Primer punto delimitante"))
      (command "pline")
      (while pto
        (command pto)
        (setq pto (getpoint))
      )
      (command "c")
      (setq polig (entlast))
    )
    (setq polig (car (entsel "Selecciona el poligono" )))
  )
  (IF (= FREC NIL)
    (setq frec "2")
  )
  (IF (= DIT NIL)
    (setq dit "1")
  )
  (IF (= DITE NIL)
    (setq dite "0.5")
  )
  (IF (= COLORT NIL)
    (setq colort "1")
  )
  (IF (= TAMT NIL)
    (setq tamt "4")
  )
  (IF (= SEPC NIL)
    (setq sepc "1")
  )
  (IF (= OPCURV NIL)
    (setq opcurv 1)
  )
  (if (not (new_dialog "opciones" dcl_id))   
    (exit)                                
                                          
  )
  (set_tile "frec" frec)
  (set_tile "dit" dit)
  (set_tile "dite" dite)
  (set_tile "colort" colort)
  (set_tile "tamt" tamt)
  (set_tile "sepc" sepc)
  (if (= opcurv 1)
    (progn
     (set_tile "si" "0")
     (set_tile "no" "1")
     (mode_tile "detall" 1)
    )
    (progn
     (set_tile "si" "1")
     (set_tile "no" "0")
     (mode_tile "detall" 0)
    )
  )
  (action_tile "si" "(opcurv1)")
  (action_tile "no" "(opcurv2)")
  (action_tile "avanzado" "(avz)")
  (action_tile "accept" "(acepta)")
  (action_tile "cancel" "(exit)")
  (start_dialog)                          
  (princ)
    (IF (= aut NIL)
      (setq aut "1")
    )
    (IF (= metodo NIL)
      (setq metodo "1")
    )
    (IF (= bdatos NIL)
      (setq bdatos "3")
    )
    (IF (= tog1 NIL)
      (setq tog1 "0")
    )
    (IF (= ints NIL)
      (setq ints "0")
    )
    (IF (= inti NIL)
      (setq inti "0")
    )
    (IF (= espr NIL)
      (setq espr "5")
    )
    (IF (= dec NIL)
      (setq dec "0")
    )
;  (COMMAND "SHELL" (strcat "C:\\Program Files\\Golden Software\\Surfer8\\Scripter\\Scripter.exe -X " RUTA "curvas.BAS"))
  (COMMAND "SHELL" (strcat "C:\\Progra~1\\Golden~1\\Surfer8\\Scripter\\Scripter.exe -x " RUTA "curvas.BAS"))
;  (COMMAND "start" "C:\\Progra~1\\Golden~1\\Surfer8\\Scripter\\Scripter.exe", 0, "-x c:\\lispmsa\\curvas.bas")
  (setq arch (open (strcat ruta "ruta.prv") "a"))
  (write-line detall arch)
  (write-line si arch)
  (write-line frec arch)
  (write-line dit arch)
  (write-line dite arch)
  (write-line colort arch)
  (write-line tamt arch)
  (write-line sepc arch)
  (write-line metodo arch)
  (write-line bdatos arch)
  (write-line tog1 arch)
  (write-line ints arch)
  (write-line inti arch)
  (write-line espr arch)
  (write-line dec arch)
  (close arch)
  (unload_dialog dcl_id)                  
  (princ)
  (setq archC (OPEN (strcat ruta "TEMP.TMP") "w"))
  (WRITE-LINE "N" ARCHC)
  (CLOSE ARCHC)
  (setq lprov "N")
  (WHILE (/= LPROV "S")
    (setq archc nil)
    (WHILE (= ARCHC NIL)
      (COMMAND "DELAY" "5000")
      (setq archC (OPEN (strcat ruta "TEMP.TMP") "r"))
    )
    (setq LPROV (READ-LINE ARCHC))
    (print lprov)
    (CLOSE ARCHC)
  )
  (COMMAND "DXFIN" (strcat ruta "NIVLOT.DXF"))
;  (SETQ GPOCURVAS (SSGET "X" '((8 . "GSLAYER"))))
;  (COMMAND "CHANGE" GPOCURVAS "" "P" "LA" "CURVASTN" "")
  (SETQ VLIMPIA 1)
  (SETQ e polig)
  (SETQ LAYCONG "GSLAYER")
  (if (= (getvar "acadver") "14.0")
    (progn
      (LOAD (STRCAT RUTA "LIMPIA14"))
      (C:LIMPI)
    )
    (progn
      (command "expresstools")
      (LOAD (STRCAT RUTA "LIMPIA"))
      (SETQ na E)
      (SETQ P1 PE)
      (C:LIMPI)
    )
  )
  (SETQ VLIMPIA 0)
)

(defun v1 ()
  (setq res "A")
  (done_dialog)
)

(defun v2 ()
  (setq res "S")
  (done_dialog)
)

(defun v3 ()
  (setq res2 "T")
  (done_dialog)
)

(defun v4 ()
  (setq res2 "G")
  (done_dialog)
)

(defun v5 ()
  (setq res3 "X")
  (done_dialog)
)

(defun v6 ()
  (setq res3 "M")
  (done_dialog)
)

(defun opcurv1 ()
  (setq opcurv 2)
  (mode_tile "detall" 0)
)

(defun opcurv2 ()
  (setq opcurv 1)
  (mode_tile "detall" 1)
)

(defun acepta ()
  (setq detall (get_tile "detall"))
  (setq si (get_tile "si"))
  (if (= si "1") (setq suaviza "s")(setq suaviza "n"))
  (setq frec (get_tile "frec"))
  (setq dit (get_tile "dit"))
  (setq dite (get_tile "dite"))
  (setq colort (get_tile "colort"))
  (setq tamt (get_tile "tamt"))
  (setq sepc (get_tile "sepc"))
  (done_dialog)
)

(defun avz ()
    (setq opnivz opniv)
    (setq metodoz metodo)
    (setq bdatosz bdatos)
    (setq tog1z tog1)
    (setq intsz ints)
    (setq intiz inti)
    (setq esprz espr)
    (setq decz dec)
    (IF (= aut NIL)
      (setq aut "1")
    )
    (IF (= metodo NIL)
      (setq metodo "1")
    )
    (IF (= bdatos NIL)
      (setq bdatos "3")
    )
    (IF (= tog1 NIL)
      (setq tog1 "0")
    )
    (IF (= ints NIL)
      (setq ints "0")
    )
    (IF (= inti NIL)
      (setq inti "0")
    )
    (IF (= espr NIL)
      (setq espr "0")
    )
    (IF (= dec NIL)
      (setq dec "0")
    )
    (if (not (new_dialog "opciones2" dcl_id))   ; Initialize the dialog.   2do dialogo
      (exit)                                ; Exit if this doesn't 
                                            ; work.
    )
    (if (= opniv 1)
      (progn
        (mode_tile "ints" 0)
        (mode_tile "inti" 0)
        (set_tile "man" "1")
        (set_tile "aut" "0")
      )
      (progn
        (mode_tile "ints" 1)
        (mode_tile "inti" 1)
        (set_tile "man" "0")
        (set_tile "aut" "1")
        (setq opniv 0)
      )
    )
    (set_tile "metodo" metodo)
    (set_tile "bdatos" bdatos)
    (set_tile "t1" tog1)
    (set_tile "ints" ints)
    (set_tile "inti" inti)
    (set_tile "espr" espr)
    (set_tile "dec" dec)
    (action_tile "aut" "(opc2)")
    (action_tile "man" "(opc22)")
    (action_tile "accept" "(aceptaop)")
    (action_tile "cancel" "(cancelaop)")
    (start_dialog)                          ; Display the dialog 
  (IF (= FREC NIL)
    (setq frec "2")
  )
  (IF (= DIT NIL)
    (setq dit "1")
  )
  (IF (= DITE NIL)
    (setq dite "0.5")
  )
  (IF (= COLORT NIL)
    (setq colort "1")
  )
  (IF (= TAMT NIL)
    (setq tamt "4")
  )
  (IF (= SEPC NIL)
    (setq sepc "1")
  )
  (IF (= OPCURV NIL)
    (setq opcurv 1)
  )
  (if (not (new_dialog "opciones" dcl_id))   
    (exit)                                
                                          
  )
  (set_tile "frec" frec)
  (set_tile "dit" dit)
  (set_tile "dite" dite)
  (set_tile "colort" colort)
  (set_tile "tamt" tamt)
  (set_tile "sepc" sepc)
  (if (= opcurv 1)
    (progn
     (set_tile "si" "0")
     (set_tile "no" "1")
     (mode_tile "detall" 1)
    )
    (progn
     (set_tile "si" "1")
     (set_tile "no" "0")
     (mode_tile "detall" 0)
    )
  )
  (action_tile "si" "(opcurv1)")
  (action_tile "no" "(opcurv2)")
  (action_tile "avanzado" "(avz)")
  (action_tile "accept" "(acepta)")
  (action_tile "cancel" "(exit)")
  (start_dialog)                          
  (princ)
)

(defun opc22 ()
   (setq opniv 1)
   (mode_tile "ints" 0)
   (mode_tile "inti" 0)
)

(defun opc2 ()
   (setq opniv 0)
   (mode_tile "ints" 1)
   (mode_tile "inti" 1)
)

(defun aceptaop ()
  (setq metodo (get_tile "metodo"))
  (setq bdatos (get_tile "bdatos"))
  (setq tog1 (get_tile "t1"))
  (setq ints (get_tile "ints"))
  (setq inti (get_tile "inti"))
  (setq espr (get_tile "espr"))
  (setq dec (get_tile "dec"))
  (done_dialog)
)

(defun cancelaop ()
  (setq metodo metodoz)
  (setq bdatos bdatosz)
  (setq tog1 tog1z)
  (setq ints intsz)
  (setq inti intiz)
  (setq espr esprz)
  (setq dec decz)
  (setq opniv opnivz)
  (done_dialog)
)
