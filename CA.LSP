;PROGRAMA PARA CALCULAR AREAS DE PREDIOS E INSERTAR NOMBRE DE PROPIETARIO
;SE REQUIERE CREAR UN BLOCK "NOMAR" CON ATRIBUTOS "NOMBRE" Y "AREA" CON
;ALTURA DE 1 Y CENTRADOS EN 0,0 NOMBRE SOBRE AREA
:CREAR PREVIO AL PROGRAMA EL LAYER "AREAS"
(DEFUN C:CA ()
     (SETQ N (GETSTRING PROMPT "DAME EL NOMBRE DEL PROPIETARIO: "))
     (SETQ XYZ (GETPOINT "DAME UN PUNTO AL CENTRO DEL AREA: "))
     (COMMAND "-BOUNDARY" XYZ "")
     (COMMAND "CHANGE" "L" "" "P" "LA" "AREAS" "")
     (COMMAND "AREA" "E" "L")
     (SETQ AP (RTOS (GETVAR "AREA") 2 3))
     (COMMAND "INSERT" (strcat ruta "blocks\\NOMAR") XYZ "" "" "" N AP)
)

(DEFUN C:CORTE ()
     (SETQ XYZ (GETPOINT "DAME UN PUNTO AL CENTRO DEL AREA: "))
     (SETQ XYZ1 XYZ)
     (SETQ AP 0)
     (WHILE XYZ
       (COMMAND "-BOUNDARY" XYZ "")
       (COMMAND "CHANGE" "L" "" "P" "LA" "AREAS" "")
       (COMMAND "AREA" "E" "L")
       (SETQ EX (ENTLAST))
       (SETQ AP (+ AP (GETVAR "AREA")))
       (SETQ XYZ (GETPOINT "DAME UN PUNTO AL CENTRO DEL AREA: <SALIR> "))
       (COMMAND "ERASE" EX "")
     )
     (SETQ AP (RTOS AP 2 3))
     (COMMAND "INSERT" (strcat ruta "blocks\\NOMAR") XYZ1 "" "" "" "CORTE" AP)
)

(DEFUN C:TERRAP ()
     (SETQ XYZ (GETPOINT "DAME UN PUNTO AL CENTRO DEL AREA: "))
     (SETQ XYZ1 XYZ)
     (SETQ AP 0)
     (WHILE XYZ
       (COMMAND "-BOUNDARY" XYZ "")
       (COMMAND "CHANGE" "L" "" "P" "LA" "AREAS" "")
       (COMMAND "AREA" "E" "L")
       (SETQ EX (ENTLAST))
       (SETQ AP (+ AP (GETVAR "AREA")))
       (SETQ XYZ (GETPOINT "DAME UN PUNTO AL CENTRO DEL AREA: <SALIR> "))
       (COMMAND "ERASE" EX "")
     )
     (SETQ AP (RTOS AP 2 3))
     (COMMAND "INSERT" (strcat ruta "blocks\\NOMAR") XYZ1 "" "" "" "TERRAP" AP)
)

(DEFUN C:DPC ()
     (SETQ XYZ (GETPOINT "DAME UN PUNTO AL CENTRO DEL AREA: "))
     (SETQ XYZ1 XYZ)
     (SETQ AP 0)
     (WHILE XYZ
       (COMMAND "-BOUNDARY" XYZ "")
       (COMMAND "CHANGE" "L" "" "P" "LA" "AREAS" "")
       (COMMAND "AREA" "E" "L")
       (SETQ EX (ENTLAST))
       (SETQ AP (+ AP (GETVAR "AREA")))
       (SETQ XYZ (GETPOINT "DAME UN PUNTO AL CENTRO DEL AREA: <SALIR> "))
       (COMMAND "ERASE" EX "")
     )
     (SETQ AP (RTOS AP 2 3))
     (COMMAND "INSERT" (strcat ruta "blocks\\NOMAR") XYZ1 "" "" "" "DC" AP)
)

(DEFUN C:DPT ()
     (SETQ XYZ (GETPOINT "DAME UN PUNTO AL CENTRO DEL AREA: "))
     (SETQ XYZ1 XYZ)
     (SETQ AP 0)
     (WHILE XYZ
       (COMMAND "-BOUNDARY" XYZ "")
       (COMMAND "CHANGE" "L" "" "P" "LA" "AREAS" "")
       (COMMAND "AREA" "E" "L")
       (SETQ EX (ENTLAST))
       (SETQ AP (+ AP (GETVAR "AREA")))
       (SETQ XYZ (GETPOINT "DAME UN PUNTO AL CENTRO DEL AREA: <SALIR> "))
       (COMMAND "ERASE" EX "")
     )
     (SETQ AP (RTOS AP 2 3))
     (COMMAND "INSERT" (strcat ruta "blocks\\NOMAR") XYZ1 "" "" "" "DT" AP)
)

(DEFUN C:CA2 ()
   (SETQ N (GETint "Numero de inicio: "))
   (while xyz
     (SETQ XYZ (GETPOINT "DAME UN PUNTO AL CENTRO DEL AREA: "))
     (if (/= xyz nil)
      (progn
        (COMMAND "-BOUNDARY" XYZ "")
        (COMMAND "CHANGE" "L" "" "P" "LA" "AREAS" "")
        (COMMAND "AREA" "E" "L")
        (SETQ AP (RTOS (GETVAR "AREA") 2 3))
        (COMMAND "INSERT" (strcat ruta "blocks\\NOMAR") XYZ "" "" "" N AP)
        (setq n (1+ n))
      )
     )
   )
)
