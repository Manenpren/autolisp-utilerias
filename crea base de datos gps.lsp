(defun c:bdgps ()
  (COMMAND "UNDO" "M")
  (C:LIBRERIA "BUSCA VALOR DE ATRIBUTO")
  (setq ARCHIVOD (getfiled "ARCHIVO DESTINO" "C:/TOPOGRAF/" "CSV" 19))
  (SETQ GPOGPS (SSGET "X" '((0 . "INSERT") (2 . "TRACKPOINT"))))
  (SETQ E (SSNAME GPOGPS 0))
  (SETQ T1 1)
  (SETQ FILE (OPEN ARCHIVOD "w"))
  (WHILE E
    (SETQ XY (cdr (assoc 10 (entget e))))
    (SETQ Y (CADR XY))
    (SETQ Y (RTOS Y 2 3))
    (SETQ X (CAR XY))
    (SETQ X (RTOS X 2 0))
    (SETQ Z (CADR XY))
    (SETQ Z (RTOS Z 2 3))
    (SETQ NUMERO (BUSATR E "TrackName"))
    (IF (= NUMERO NIL) (SETQ NUMERO "1"))
    (SETQ LINEAW (STRCAT X "," Y "," Z "," NUMERO "GPS"))
    (WRITE-LINE LINEAW FILE)
    (PRINT NUMERO)
    (SETQ E (SSNAME GPOGPS T))
    (SETQ T1 (1+ T1))
  )
  (CLOSE FILE)
)
