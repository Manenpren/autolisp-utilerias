(defun C:cb ()
    (setq NUMERO (getstring "numero de cambio : " ))
    (setq f (getint "numero de textos : " ))
    (setq T1 0)
    (while (/= T1 f)
        (setq T1 (+ T1 1))
        (setq e (car (entsel "Selecciona EL TEXTO: ")))
        (setq NOMBRE (cdr (assoc 1 (entget e))))
        (setq nomblo (strcat NOMBRE "-" NUMERO))
        (command "change" e "" "" "" "" "" "" nomblo)
    )
)
