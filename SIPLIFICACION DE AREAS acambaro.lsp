(defun c:SAF ()
  (C:LIBRERIA "BUSCA VALOR DE ATRIBUTO")
  (C:LIBRERIA "AREA OBTENIDA EN UN PUNTO")
  (C:LIBRERIA "ASOCIASIONES")
  (C:LIBRERIA "ZOOM ULTIMO OBJETO INSERTADO")
  (COMMAND "UNDO" "M")
  (COMMAND "VIEW" "S" "C")
  (setq PROV (CAR (ENTSEL "SELECCIONA BLOCK")))
  (setq NOMBLO (cdr (assoc 2 (entget PROV))))
  (COMMAND "INSERT" NOMBLO "0,0" "" "" "")
  (SETQ X (ENTLAST))
  (ZBLOCK)
;  (COMMAND "EXPLODE" X "")
  (SETQ GPOA (SSGET "P"))
  (SETQ P 1)
  (SETQ PROV (SSNAME GPOA 0))
  (WHILE PROV
    (IF (= (cdr (assoc 0 (entget PROV))) "TEXT")                      ;ASLKHASLDHSAHDSÑADLHLÑHJSÑADSAD
      (PROGN
        (SETQ VTEXT (cdr (assoc 1 (entget PROV))))
        (IF (= (SUBSTR VTEXT 1 2) "Rs")
          (SETQ VRAS (SUBSTR VTEXT 3 (- (STRLEN VTEXT) 2)))
        )
        (IF (= (SUBSTR VTEXT 1 2) "Tn")
          (SETQ VTN (SUBSTR VTEXT 3 (- (STRLEN VTEXT) 2)))
        )
      )
    )
    (SETQ PROV (SSNAME GPOA P))
    (SETQ P (1+ P))
  )
  (SETQ AREACORTE 0)
  (SETQ AT 0)
  (SETQ ADC 0)
  (SETQ ADT 0)
  (SETQ NOMBREP nil)
  (SETQ NOMBREP2 nil)
  (SETQ NOMBREP3 nil)
  (SETQ NOMBREP4 nil)
  (SETQ AREAP nil)
  (SETQ AREAP2 nil)
  (SETQ AREAP3 nil)
  (SETQ AREAP4 nil)
  (SETQ P 0)
  (SETQ PROV (SSNAME GPOA P))
  (setq p (1+ p))
  (WHILE (/= (cdr (assoc 0 (entget PROV))) "INSERT")
    (IF (/= PROV nil)
     (SETQ PROV (SSNAME GPOA P))
    )
    (SETQ P (1+ P))
  )
  (IF (/= PROV nil)
   (PROGN
    (SSDEL PROV GPOA)
    (SETQ NOMBREP (BUSATR PROV "NOMBRE"))  
    (SETQ AREAP (BUSATR PROV "AREA"))  
    (COMMAND "ERASE" PROV "")
   )
  )
  (setq p 0)
  (SETQ PROV (SSNAME GPOA P))
  (IF (/= PROV nil)
   (PROGN
    (SETQ ATT (cdr (assoc 0 (entget PROV))))
    (WHILE (AND (/= ATT "INSERT") (/= PROV nil))
      (SETQ PROV (SSNAME GPOA P))
      (IF (/= PROV nil)
        (SETQ ATT (cdr (assoc 0 (entget PROV))))
      )
      (SETQ P (1+ P))
    )
    (IF (/= PROV nil)
     (PROGN
      (SETQ NOMBREP2 (BUSATR PROV "NOMBRE"))  
      (SETQ AREAP2 (BUSATR PROV "AREA"))  
      (SSDEL PROV GPOA)
      (COMMAND "ERASE" PROV "")
     )
    )
   )
  )
  (setq p 3)
  (SETQ PROV (SSNAME GPOA P))
  (IF (/= PROV nil)
   (PROGN
    (SETQ ATT (cdr (assoc 0 (entget PROV))))
    (WHILE (AND (/= ATT "INSERT") (/= PROV nil))
      (SETQ PROV (SSNAME GPOA P))
      (IF (/= PROV nil)
        (SETQ ATT (cdr (assoc 0 (entget PROV))))
      )
      (SETQ P (1+ P))
    )
    (IF (/= PROV nil)
     (PROGN
      (SETQ NOMBREP3 (BUSATR PROV "NOMBRE"))  
      (SETQ AREAP3 (BUSATR PROV "AREA"))  
      (SSDEL PROV GPOA)
      (COMMAND "ERASE" PROV "")
     )
    )
   )
  )
  (setq p 3)
  (SETQ PROV (SSNAME GPOA P))
  (IF (/= PROV nil)
   (PROGN
    (SETQ ATT (cdr (assoc 0 (entget PROV))))
    (WHILE (AND (/= ATT "INSERT") (/= PROV nil))
      (SETQ PROV (SSNAME GPOA P))
      (IF (/= PROV nil)
        (SETQ ATT (cdr (assoc 0 (entget PROV))))
      )
      (SETQ P (1+ P))
    )
    (IF (/= PROV nil)
     (PROGN
      (SETQ NOMBREP4 (BUSATR PROV "NOMBRE"))  
      (SETQ AREAP4 (BUSATR PROV "AREA"))  
      (SSDEL PROV GPOA)
      (COMMAND "ERASE" PROV "")
     )
    )
   )
  )
  (IF (= NOMBREP "CORTE") (SETQ AREACORTE (RTOS (ATOF AREAP) 2 3)))
  (IF (= NOMBREP "TERRAP") (SETQ AT (RTOS (ATOF AREAP) 2 3)))
  (IF (= NOMBREP "DC") (SETQ ADC (RTOS (ATOF AREAP) 2 3)))
  (IF (= NOMBREP "DT") (SETQ ADT (RTOS (ATOF AREAP) 2 3)))
  (IF (= NOMBREP2 "CORTE") (SETQ AREACORTE (RTOS (ATOF AREAP2) 2 3)))
  (IF (= NOMBREP2 "TERRAP") (SETQ AT (RTOS (ATOF AREAP2) 2 3)))
  (IF (= NOMBREP2 "DC") (SETQ ADC (RTOS (ATOF AREAP2) 2 3)))
  (IF (= NOMBREP2 "DT") (SETQ ADT (RTOS (ATOF AREAP2) 2 3)))
  (IF (= NOMBREP3 "CORTE") (SETQ AREACORTE (RTOS (ATOF AREAP3) 2 3)))
  (IF (= NOMBREP3 "TERRAP") (SETQ AT (RTOS (ATOF AREAP3) 2 3)))
  (IF (= NOMBREP3 "DC") (SETQ ADC (RTOS (ATOF AREAP3) 2 3)))
  (IF (= NOMBREP3 "DT") (SETQ ADT (RTOS (ATOF AREAP3) 2 3)))
  (IF (= NOMBREP4 "CORTE") (SETQ AREACORTE (RTOS (ATOF AREAP4) 2 3)))
  (IF (= NOMBREP4 "TERRAP") (SETQ AT (RTOS (ATOF AREAP4) 2 3)))
  (IF (= NOMBREP4 "DC") (SETQ ADC (RTOS (ATOF AREAP4) 2 3)))
  (IF (= NOMBREP4 "DT") (SETQ ADT (RTOS (ATOF AREAP4) 2 3)))
  (IF (= ADC NIL) (SETQ ADC "0"))
  (IF (= ADT NIL) (SETQ ADT "0"))
  (IF (= AREACORTE NIL) (SETQ AREACORTE "0"))
  (IF (= AT NIL) (SETQ AT "0"))
;  (IF (/= POLTN NIL)
;    (COMMAND "CHANGE" POLTN "" "P" "LA" "LINEAS" "")
;  )
;  (IF (/= POLTN2 NIL)
;    (COMMAND "CHANGE" POLTN2 "" "P" "LA" "LINEAS" "")
;  )
;  (COMMAND "ZOOM" "C" (STRCAT "0," VRAS) "20")
;  (command "layer" "off" "reticula" "off" "LINEAS" "")
;  (COMMAND "-BOUNDARY" (STRCAT "0," (RTOS (- (ATOF VRAS) 0.025)2 3)) "")   ;CICLO
;  (COMMAND "CHANGE" "L" "" "P" "LA" "AREAS" "")
;  (COMMAND "AREA" "E" "L")
;  (SETQ EX (ENTLAST))
;  (SETQ ACARP (rtos (GETVAR "AREA") 2 3))
;  (SETQ VALOR (GETSTRING "\n AREA CORRECTA (S/N) <S> :"))
;  (IF (= VALOR "") (SETQ VALOR "S"))
;  (IF (= (STRCASE VALOR) "S") (COMMAND "ERASE" EX "") (EXIT))                ;FIN CICLO
;  (COMMAND "-BOUNDARY" (STRCAT "0," (RTOS (- (ATOF VRAS) 0.15) 2 3)) "")   ;CICLO
;  (COMMAND "CHANGE" "L" "" "P" "LA" "AREAS" "")
;  (COMMAND "AREA" "E" "L")
;  (SETQ EX (ENTLAST))
;  (SETQ ABASE (rtos (GETVAR "AREA") 2 3))
;  (SETQ VALOR (GETSTRING "\n AREA CORRECTA (S/N) <S> :"))
;  (IF (= VALOR "") (SETQ VALOR "S"))
;  (IF (= (STRCASE VALOR) "S") (COMMAND "ERASE" EX "") (EXIT))                ;FIN CICLO
;  (COMMAND "-BOUNDARY" (STRCAT "0," (RTOS (- (ATOF VRAS) 0.35) 2 3)) "")   ;CICLO
;  (COMMAND "CHANGE" "L" "" "P" "LA" "AREAS" "")
;  (COMMAND "AREA" "E" "L")
;  (SETQ EX (ENTLAST))
;  (SETQ ASUBR (rtos (GETVAR "AREA") 2 3))
;  (SETQ VALOR (GETSTRING "\n AREA CORRECTA (S/N) <S> :"))
;  (IF (= VALOR "") (SETQ VALOR "S"))
;  (IF (= (STRCASE VALOR) "S") (COMMAND "ERASE" EX "") (EXIT))                ;FIN CICLO
;  (COMMAND "-BOUNDARY" (STRCAT "0," (RTOS (- (ATOF VRAS) 0.65) 2 3)) "")   ;CICLO
;  (COMMAND "CHANGE" "L" "" "P" "LA" "AREAS" "")
;  (COMMAND "AREA" "E" "L")
;  (SETQ EX (ENTLAST))
;  (SETQ AFILTRO (rtos (GETVAR "AREA") 2 3))
;  (SETQ VALOR (GETSTRING "\n AREA CORRECTA (S/N) <S> :"))
;  (IF (= VALOR "") (SETQ VALOR "S"))
;  (IF (= (STRCASE VALOR) "S") (COMMAND "ERASE" EX "") (EXIT))                ;FIN CICLO
;  (SETQ PINS (GETPOINT "DAME EL PUNTO DE INSERCION DE LAS AREAS "))
  (COMMAND "INSERT" "AREAS" PAUSE "1.2" "" "" "0+000" "1" "1" "1" "1" "1" "1" "1" "1" "1" "0" "0" "0" "0" "" "" "" "" "" "" "" "" "" "" "" "" "" "")
; AREACORTE CAD RASAN TN DCORTE DTERRAP CORTE TERRAP FILTRO SUBR BASE CARPETA BANQ MBANQ
  (SSADD (ENTLAST) GPOA)
;  (setq bl (car(entsel "selecciona el block destino")))
  (setq bl (entnext (entlast)))
  (COMMAND "attedit" "" "" "" "" bl "V" "R" NOMBLO "")
  (setq bl (entnext BL))
  (COMMAND "attedit" "" "" "" "" bl "V" "R" VRAS "")
  (setq bl (entnext BL))
  (COMMAND "attedit" "" "" "" "" bl "V" "R" VTN "")
  (setq bl (entnext BL))
  (COMMAND "attedit" "" "" "" "" bl "V" "R" ADC "")
  (setq bl (entnext BL))
;  (COMMAND "attedit" "" "" "" "" bl "V" "R" ADT "")
;  (setq bl (entnext BL))
  (COMMAND "attedit" "" "" "" "" bl "V" "R" AREACORTE "")
  (setq bl (entnext BL))
  (COMMAND "attedit" "" "" "" "" bl "V" "R" AT "")
  (setq bl (entnext BL))
  (COMMAND "attedit" "" "" "" "" bl "V" "R" "8.400" "")
  (setq bl (entnext BL))
  (COMMAND "attedit" "" "" "" "" bl "V" "R" "3.600" "")
  (setq bl (entnext BL))
  (COMMAND "attedit" "" "" "" "" bl "V" "R" "2.976" "")
  (setq bl (entnext BL))
  (COMMAND "attedit" "" "" "" "" bl "V" "R" "0.720" "")
  (setq bl (entnext BL))
  (COMMAND "attedit" "" "" "" "" bl "V" "R" "0.400" "")
  (setq bl (entnext BL))
  (COMMAND "attedit" "" "" "" "" bl "V" "R" "0.160" "")
  (setq bl (entnext BL))
  (COMMAND "attedit" "" "" "" "" bl "V" "R" "0.000" "")
  (command "layer" "t" "*" "")
  (command "layer" "ON" "*" "")
  (COMMAND "BLOCK" NOMBLO "Y" "0,0" GPOA "")
  (COMMAND "VIEW" "R" "C")
)
