(defun c:mimg1 ()
  (C:LIBRERIA "SEXAGESIMALtoDECIMAL")
  (C:LIBRERIA "GEO-UTM")
  (PROMPT "SELECCIONA LOS objetos a mover")
  (setq gpom (ssget))
  (SETQ xyz (GETPOINT "\n Primer punto base "))
  (SETQ pgeola (GETSTRING PROMPT "\n Punto destino lat(g m s.ssss) :"))
  (SETQ pgeolo (GETSTRING PROMPT "\n Punto destino long(g m s.ssss) :"))
  (setq pgeola (revisa pgeola))
  (setq pgeolo (revisa pgeolo))
  (setq pgeola (SEXADEC pgeola))
  (setq pgeolo (SEXADEC pgeolo))
  (setq puntogeo (list pgeolo pgeola))
  (setq puntoutm (GEO-UTM puntogeo))
  (SETQ xyz2 (GETPOINT "\n Segundo punto base "))
  (SETQ pgeola (GETSTRING PROMPT "\n Punto destino lat(g m s.ssss) :"))
  (SETQ pgeolo (GETSTRING PROMPT "\n Punto destino long(g m s.ssss) :"))
  (setq pgeola (revisa pgeola))
  (setq pgeolo (revisa pgeolo))
  (setq pgeola (SEXADEC pgeola))
  (setq pgeolo (SEXADEC pgeolo))
  (setq puntogeo2 (list pgeolo pgeola))
  (setq puntoutm2 (GEO-UTM puntogeo2))
  (command "align" gpom "" xyz puntoutm xyz2 puntoutm2 "" "y")
)

(defun revisa (prov)
  (setq sumav 0)
  (if (not (WCMATCH prov "* *"))
    (progn
      (if (= (substr prov 1 1) "-") (setq sumav 1))
      (if (> (abs (atof prov)) 999999.99999999)
        (progn
           (setq grd (substr prov (+ sumav 1) 3))
           (setq minu (substr prov (+ sumav 4) 2))
           (setq sec (substr prov (+ sumav 6) (- (strlen prov) (+ sumav 5))))
        )
        (progn
           (setq grd (substr prov (+ sumav 1) 2))
           (setq minu (substr prov (+ sumav 3) 2))
           (setq sec (substr prov (+ sumav 5) (- (strlen prov) (+ sumav 4))))
        )
      )
      (if (= sumav 1)
       (setq prov (strcat "-" grd " " minu " " sec))
       (setq prov (strcat grd " " minu " " sec))
      )
    )
  )
  (setq prov prov)
)
