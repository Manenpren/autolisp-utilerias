(defun vertice (poli nov)
  (setq listap (entget poli))
  (setq nver 0)
  (setq salir "N")
  (while (= salir "N")
    (setq sublisp (car listap))
    (if (= 10 (car sublisp))
      (progn
        (setq punto (cdr sublisp))   
        (setq nver (+ nver 1))
      )
    )
    (setq listap (cdr listap))
    (if listap
      (setq salir "N")
      (setq salir "S")
    )
    (if (= nov nver)
      (setq salir "S")
    )
  )
  (if (not listap)
    (setq punto nil)
  )
  (setq punto punto)
)


(defun c:EPP2 ()
  (setq NomArch (getfiled "ARCHIVO A CREAR " "*." "CSV" 19))
  (write-line "Selecciona las polylineas a procesar")
  (setq GpoPol (ssget))
  (setq Arch (open NomArch "w"))
  (setq cuenta 0)
  (while (/= cuenta (sslength GpoPol))
    (setq e (ssname GpoPol cuenta))
    (if (= "LWPOLYLINE" (cdr (assoc 0 (entget e))))
      (progn
        (setq nnver 1)
        (while (vertice e nnver)
          (setq vvert (vertice e nnver))
          (write-line (strcat (rtos nnver 2 0) "," (rtos (car vvert) 2 3) "," (rtos (car (cdr vvert)) 2 3) "," (RTOS (cdr (assoc 38 (entget e))) 2 4)) Arch)
          (setq nnver (+ nnver 1))
        )
      )
    )
    (setq cuenta (+ cuenta 1))
  )
  (close arch)
)
