(defun c:htext1 ()
        (setq e (car (entsel "Selecciona el texto a escalar: ")))
        (setq fs (cdr (assoc 40 (entget e))))
        (setq HF (getreal "Tamaño final del texto : "))
        (setq E (entnext))
        (while E
          (if (= "TEXT" (cdr (assoc 0 (entget E)))) 
            (if (= fs (cdr (assoc 40 (entget E))))
              (entmod (subst (cons 40 HF) (assoc 40 (entget E)) (entget E)))
            )
          )
          (setq E (entnext E))
        )
)
