(defun vertice (poli nov)
  (setq listap (entget poli))
  (setq nver 0)
  (setq salir "N")
  (while (= salir "N")
    (setq sublisp (car listap))
    (if (= 10 (car sublisp))
      (progn
        (setq punto (cdr sublisp))   
        (setq nver (+ nver 1))
      )
    )
    (setq listap (cdr listap))
    (if listap
      (setq salir "N")
      (setq salir "S")
    )
    (if (= nov nver)
      (setq salir "S")
    )
  )
  (if (not listap)
    (setq punto nil)
  )
  (setq punto punto)
)


(defun c:EPP3 ()
  (write-line "Selecciona las polylineas a procesar")
  (setq GpoPol (ssget))
  (setq cuenta 0)
  (while (/= cuenta (sslength GpoPol))
    (setq e (ssname GpoPol cuenta))
    (if (OR (= "LWPOLYLINE" (cdr (assoc 0 (entget e)))) (= "POLYLINE" (cdr (assoc 0 (entget e)))))
     (PROGN
      (setq vz (cdr (assoc 38 (entget e))))
      (command "-layer" "N" (RTOS VZ 2 0) "")
      (COMMAND "CHANGE" E "" "P" "LA" (RTOS VZ 2 0) "")
     )
    )
    (setq cuenta (+ cuenta 1))
  )
)
