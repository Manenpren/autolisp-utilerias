(load (strcat rutaFAS "funciones_sec"))
(defun CadNum (NOMBRE)
  (SETQ LNG (STRLEN NOMBRE))
  (SETQ NOMBLO "")
  (SETQ CONT 0)
  (REPEAT LNG
    (SETQ CONT (1+ CONT))
    (setq CARACTER (substr NOMBRE CONT 1))
    (IF (= CARACTER "+") (SETQ CARACTER ""))
    (setq nomblo (STRCAT NOMBLO CARACTER))
  )
  (setq CadNumVar NomBlo)
)

(defun CadNum2 (NOMBRE)
  (SETQ LNG (STRLEN NOMBRE))
  (SETQ NOMBLO "")
  (SETQ CONT 0)
  (REPEAT LNG
    (SETQ CONT (1+ CONT))
    (setq CARACTER (substr NOMBRE CONT 1))
    (IF (= CARACTER "+") (SETQ CARACTER "-"))
    (setq nomblo (STRCAT NOMBLO CARACTER))
  )
  (setq CadNumVar NomBlo)
)

(defun CadNum3 (NOMBRE)
  (SETQ LNG (STRLEN NOMBRE))
  (SETQ NOMBLO "")
  (SETQ CONT 0)
  (REPEAT LNG
    (SETQ CONT (1+ CONT))
    (setq CARACTER (substr NOMBRE CONT 1))
    (IF (= CARACTER "-") (SETQ CARACTER ""))
    (setq nomblo (STRCAT NOMBLO CARACTER))
  )
  (setq CadNumVar NomBlo)
)

(defun valcap (NL)
  (setq prov2 1)
  (while (/= "." (substr NL prov2 1))
    (setq prov2(1+ prov2))
  )
  (setq NL (strcat (substr NL 1 (1- prov2)) "-" (substr NL (1+ prov2) 3)))
  (setq valcap NL)
)

(defun C:CreaCFG ()
  (setq opescaneo "0")
  (SETQ ANCHO "20")
  (SETQ ESCALACAD "0.7")
  (SETQ LTN "TN")
  (SETQ LRET "RETICULA")
  (SETQ LTRET "RETICULA")
  (SETQ LCAD "TN")
  (SETQ LNIV "TN")
  (SETQ SHL "1")
  (SETQ SVL "5")
  (SETQ ETLH "1")
  (SETQ ETLV "1")
  (SETQ STRET "0.3")
  (SETQ CTN "3")
  (SETQ CRET "2")
  (SETQ CTRET "6")
  (SETQ CCAD "7")
  (SETQ CNIV "7")
  (setq dcl_id (load_dialog (strcat ruta "dialogos\\seccion.dcl"))) ; Load the DCL file.
  (if (not (new_dialog "SEC" dcl_id))   ; Initialize the dialog.
    (exit)                                ; Exit if this doesn't 
                                          ; work.
  )
  (set_TILE "ancho" ancho)
  (set_TILE "scad" escalacad)
  (action_tile "actualiza" "(dibujo)")
  (action_tile "ancho" "(var)")
  (action_tile "scad" "(var2)")
  (action_tile "escan" "(var23)")
  (action_tile "reticula" "(exa)")
  (action_tile "capas" "(exa2)")
  (action_tile "cfgf" "(exa3)")
  (action_tile "save" "(exa4)")
  (action_tile "colores" "(exa5)")
  (action_tile "accept" "(aceptas)")
  (action_tile "imagen" "(aceptx)")
  (start_dialog)                          ; Display the dialog 
                                          ; box.
  (unload_dialog dcl_id)                  ; Unload the DCL file.
  (princ)
)

(defun aceptx ()
  (setq xxxf (get_attr "imagen" "dimx_tile"))
  (alert xxxf)
)

(defun suma (punto xx yy)
  (setq xxx (car punto))
  (setq yyy (car (cdr punto)))
  (setq xxx (+ xxx xx))
  (setq yyy (+ yyy yy))
  (list xxx yyy)
)

(defun asigna ()
  (setq xm (car (cdr (assoc 10 (entget ob)))))
  (setq xml ele2)
)

(defun redo5 (daton)
  (setq daton (rtos daton 2 3))
  (setq cara (substr daton 1 1))
  (setq cuecar 1)
  (setq encpun 0)
  (setq pospun 0)
  (while (/= cara "")
    (setq cara (substr daton cuecar 1))
    (if (= cara ".")
      (progn
        (setq encpun 1)
        (setq pospun cuecar)
      )
    )
    (setq cuecar (+ cuecar 1))
  )    
  (if (= encpun 1)
    (progn
      (if (= (strlen daton) 1)            
        (setq daton daton)
      )
      (setq numdec (strlen (substr daton pospun)))
      (setq daton (substr daton 1 (- (strlen daton) numdec)))
    )
    (setq daton daton)
  )

;  (setq ultimo (atof (substr daton (strlen daton) 1)))
;  (if (/= ultimo 0)
;    (progn
;      (setq inicio (substr daton 1 (- (strlen daton) 1)))
;      (if (> 6 ultimo)
;        (setq daton (atof (strcat inicio "5")))
;        (setq daton (+ (atof (strcat inicio "0")) 10))
;      )
;    )
;    (setq daton (atof daton))
;  )
  (setq daton (atof daton))
)


(defun ordenax ()
  (setq ele2 0)
  (setq xlm 0)
  (setq ob (ssname gpo ele2))
  (setq xm (car (cdr (assoc 10 (entget ob)))))  
  (while ob
    (if (>= (car (cdr (assoc 10 (entget ob)))) xm)
      (asigna)
    )
    (setq ele2 (+ ele2 1))
    (setq ob (ssname gpo ele2))
  )
)

(defun cadena ()
  (setq cad ob)
  (setq cadtex (cdr (assoc 1 (entget cad))))
  (setq numtxt ele)
)

(defun ordena ()
  (setq ele 0)
  (setq ob (ssname gpo ele))
  (while ob
    (if (= "LINE" (cdr (assoc 0 (entget ob))))
      (setq numli ele)
    )
    (if (= "TEXT" (cdr (assoc 0 (entget ob))))
      (cadena)
    )
    (setq ele (+ ele 1))
    (setq ob (ssname gpo ele))
  )
  (setq gpoo (ssadd (ssname gpo numtxt)))
  (setq gpoo (ssadd (ssname gpo numli)))
  (ssdel (ssname gpo numli) gpo)
  (if (> numtxt numli)
    (setq numtxt (- numtxt 1))
  )
  (ssdel (ssname gpo numtxt) gpo)

  (setq ele 0)
  (setq ele2 0)
  (setq ob (ssname gpo ele))
  (while (/= ele (- eleme 2))
    (ordenax)
    (ssadd (ssname gpo xml) gpoo)
    (ssdel (ssname gpo xml) gpo)
    (setq ele (+ ele 1))
  )
)

(defun ordena2 ()
  (setq ele 0)
  (setq ob (ssname gpo ele))
  (while ob
    (if (= "LINE" (cdr (assoc 0 (entget ob))))
      (setq numli ele)
    )
    (setq ele (+ ele 1))
    (setq ob (ssname gpo ele))
  )
  (setq gpoo (ssadd (ssname gpo numli)))
  (ssdel (ssname gpo numli) gpo)

  (setq ele 0)
  (setq ele2 0)
  (setq ob (ssname gpo ele))
  (while (/= ele (- eleme 1))
    (ordenax)
    (ssadd (ssname gpo xml) gpoo)
    (ssdel (ssname gpo xml) gpo)
    (setq ele (+ ele 1))
  )
)


(defun ver1 ()
  (setq ele 0)
  (setq ob (ssname gpoo ele))
  (while ob
    (prin1 (entget ob))
    (write-line " ")
    (setq ele (+ ele 1))
    (setq ob (ssname gpoo ele))
  )
)

(defun ver2 ()
  (setq ele 0)
  (setq ob (ssname gpo ele))
  (while ob
    (prin1 (entget ob))
    (write-line " ")
    (setq ele (+ ele 1))
    (setq ob (ssname gpo ele))
  )
)

(defun mueve ()
  (setq p11 (suma (cdr (assoc 10 (entget (ssname gpoo 0)))) 0.1 0.1))
  (setq p12 (suma (cdr (assoc 10 (entget (ssname gpoo 0)))) -0.1 -0.1))
  (command "ZOOM" "w" p11 p12)
;  (SETQ GPO (ENTGET CAD))
;  (PRINT GPO)
;  (SETQ XOB1 (CDR (assoc 10 (entget (ssname GPO 0)))))
;  (SETQ XOB2 (CDR (assoc 10 (entget (ssname GPO (sslength GPO))))))
;  (SETQ PX1 (CAR XOB1))
;  (SETQ PY1 (CADR XOB1))
;  (SETQ PX2 (CAR XOB2))
;  (SETQ PY2 (CADR XOB2))
;  (IF (= PX1 PX2)
;    (SETQ MX PX1)
;    (SETQ MX (/ (ABS (- PX1 PX2)) 2))
;  )
;  (IF (= PY1 PY2)
;    (SETQ MY PY1)
;    (SETQ MY (/ (ABS (- PY1 PY2)) 2))
;  )
;  (IF (> PX1 PX2)
;    (SETQ MX (+ PX2 MX))
;    (SETQ MX (+ PX1 MX))
;  )
;  (IF (> PY1 PY2)
;    (SETQ MY (+ PY2 MY))
;    (SETQ MY (+ PY1 MY))
;  )
;  (SETQ MY (RTOS MY 2 6))
;  (SETQ MX (RTOS MX 2 6))
;  (SETQ MITAD (STRCAT MX "," MY))
;  (command "MOVE" gpoo cad "" MITAD "0,0")
  (setq ligpoo (ssname gpoo 0))
  (setq pun1 (cdr (assoc 10 (entget ligpoo)))) 
  (setq pun2 (cdr (assoc 11 (entget ligpoo)))) 
  (setq x1 (car pun1))
  (setq y1 (car (cdr pun1)))
  (setq x2 (car pun2))
  (setq y2 (car (cdr pun2)))
  (setq xd (- x1 x2))
  (if (> 0 xd)
    (setq xd (* xd -1))
  )
  (setq xd (/ xd 2))

  (setq yd (- y1 y2))
  (if (> 0 yd)
    (setq yd (* yd -1))
  )
  (setq yd (/ yd 2))
  (if (> x1 x2)
    (setq xd (+ xd x2))
    (setq xd (+ xd x1))
  )
  (if (> y1 y2)
    (setq yd (+ yd y2))
    (setq yd (+ yd y1))
  )
  (setq punmid (list xd yd))  

  (COMMAND "-LAYER" "SET" "PROV" "")
  (command "CIRCLE" PUNMID "1")
  (command "COPY" gpoo cad "" punmid punmid)
  (command "MOVE" gpoo cad "" punmid "0,0")
  (command "ZOOM" "c" "0,0" (+ (distance pun1 pun2) 6))
)

(defun rota ()
  (setq p1 (cdr (assoc 10 (entget (ssname gpoo 0)))))
  (setq p2 (cdr (assoc 11 (entget (ssname gpoo 0)))))
  (setq angulo (- 360.0 (atof (angtos (angle p1 p2) 0 8))))
  (command "ROTATE" gpoo cad "" "0,0" angulo)
  (setq r1 (getstring "\n Rotar 180 <N>:"))
  (if (= (strcase r1) "S")
    (command "ROTATE" gpoo cad "" "0,0" "180")
  )
)

(defun ez (obje)
  (setq obje (entnext obje))
  (if (= "ELEV" (strcase (cdr (assoc 2 (entget obje)))))
    (setq eleva (cdr (assoc 1 (entget obje))))
  )
  (setq obje (entnext obje))
  (if (= "ELEV" (strcase (cdr (assoc 2 (entget obje)))))
    (setq eleva (cdr (assoc 1 (entget obje))))
  )
  (setq obje (entnext obje))
  (if (= "ELEV" (strcase (cdr (assoc 2 (entget obje)))))
    (setq eleva (cdr (assoc 1 (entget obje))))
  )
  (setq elev (atof eleva))
)

(defun traza ()
  (setq ele 1)
  (setq ob1 (ssname gpoo ele))
  (setq p1 (cdr (assoc 10 (entget ob1))))
  (setq zm (ez ob1))
  (setq zn (ez ob1))
  (setq ob2 ob1)
  (setq salir 1)
  (setq gpoo2 (ssadd))
  (COMMAND "-LAYER" "SET" CAPTEN "")
    (setq x1 (car p1))
    (setq z1 (ez ob1))
    (setq p1r (list x1 z1))
  (command "PLINE" P1R)
  (while salir
    (setq ele (+ ele 1))
    (setq ob2 (ssname gpoo ele))
    (setq p2 (cdr (assoc 10 (entget ob2))))
    (setq x1 (car p1))
    (setq x2 (car p2))
    (setq z1 (ez ob1))
    (setq z (ez ob2))
    (if (> z zm)
      (setq zm z)
    )
    (if (< z zn)
      (setq zn z)
    )
    (setq z2 (ez ob2))
    (setq p1r (list x1 z1))
    (setq p2r (list x2 z2))
    (command p2r)
    (setq p1 p2)
    (setq ob1 ob2)
    (setq salir (ssname gpoo (+ ele 1)))
  )
  (COMMAND "")
  (SETQ POLIL (entlast))
  (COMMAND "COPY" (ENTLAST) "" "0,0" "0,0")
  (COMMAND "EXPLODE" (ENTLAST) "")
  (SETQ GPOO2 (SSGET "P"))
)


(defun inserta ()
  (setq cco (ssname gpoo 1))
  (setq cco (entnext cco)) (setq cco (entnext cco))
  (setq cco (cdr (assoc 1 (entget cco))))
  (setq cco (- (atof cco) 3.5))
  (setq cco2 (- cco 5))
  (setq cco3 (- cco 10))
  (command "LINE" (strcat "0," (rtos (- cco3 1000) 2 2)) "@9000<90" "")
  (setq linv (entlast))
  (setq pl1 (cdr (assoc 10 (entget linv))))
  (setq pl2 (cdr (assoc 11 (entget linv))))
  (setq lina (ssname gpoo2 0))
  (setq cuenta 0)
  (while (/= cuenta (sslength gpoo2))
    (setq pl3 (cdr (assoc 10 (entget lina))))
    (setq pl4 (cdr (assoc 11 (entget lina))))
    (setq nivel (inters pl1 pl2 pl3 pl4 T))
    (setq cuenta (+ cuenta 1))
    (setq lina (ssname gpoo2 cuenta))
    (if nivel
      (setq cuenta (sslength gpoo2))
    )
  )
  (setq ycco1 (+ cco 10)) (setq ycco2 (- cco 10))
  (command "ZOOM" "W" (strcat (rtos (+ ancho 20)) "," (rtos ycco1 2 2)) (strcat (rtos (* (+ ancho 20) -1)) "," (rtos ycco2 2 2)))
  (command "VIEW" "S" "S")
  (setq cco (strcat "0," (rtos cco 2 2)))
  (command "MOVE" gpoo cad "" "0,0" (strcat "0," (rtos cco2 2 2)))
  (SETQ XYZX (CONS 10 nivel))
  (SETQ XYZX2 (CONS 11 nivel))
  (setq colorcot (cons 62  (atoi ccad)))
  (setq tamanot (cons 40 (atof escalacad)))
  (setq layert (cons 8 lcad))                            
  (setq nivel2 (car (cdr nivel)))
  (setq nivv (entlast))
  (entdel linv)
  (if (> nivel2 0) (setq signo "+") (setq signo ""))
  (SETQ TEXTX (CONS 1 (strcat "Tn" signo (rtos nivel2 2 3))))
  (ENTMAKE (LIST '(0 . "TEXT") '(100 . "AcDbEntity") layert '(100 . "AcDbText") XYZX tamanot TEXTX colorcot '(7 . "ROMANS") '(72 . 1) xyzx2 '(73 . 1)))
  (setq nivv (entlast))
  (SETQ TEXTX (CONS 1 cadtex))
  (ENTMAKE (LIST '(0 . "TEXT") '(100 . "AcDbEntity") layert '(100 . "AcDbText") XYZX tamanot TEXTX colorcot '(7 . "ROMANS") '(72 . 1) xyzx2 '(73 . 3)))
  (setq cadt (entlast))
  (setq cadtexx (CadNum cadtex))
;  (setq gpox (ssadd))
;  (command "insert" "t2" nivel "" "" "")     ;inserta bloque inventado
;  (ssadd (entlast) gpox)
)

(defun reticula ()
  (setq ym (car (cdr (assoc 10 (entget (ssname gpoo2 0))))))
  (setq yn (car (cdr (assoc 11 (entget (ssname gpoo2 (- (sslength gpoo2) 1)))))))
;  (setq ym1 (atof (rtos (+ ym 1) 2 0)))
;  (setq yn1 (atof (rtos (- yn 1) 2 0)))
  (if (/= opescaneo "1")
    (progn
      (setq ym1 ancho)
      (setq yn1 ancho)
    )
  )
  (if (= opescaneo "1")
    (progn
;      (setq ym1 (* sepret2 (1+ (fix (/ (- anchoxxx anchoxxx1) sepret2)))))
      (setq ym1 (abs (* sepret2 (1- (fix (/ anchoxxx1 sepret2))))))
      (setq yn1 (abs (* sepret2 (1+ (fix (/ anchoxxx sepret2))))))
;      (setq yn1 (* sepret2 (1+ (fix (/ (- anchoxxx anchoxxx1) sepret2)))))
    )
  )
  (setq zm1 (redo5 (+ zm 1)))
  (setq zn1 (redo5 (- zn 2)))
  (setq gporet (ssadd))
  (command "LAYER" "M" lret "")
  (command "LAYER" "S"lret "")
;  (command "LINE" (strcat "0," (rtos zn1)) (strcat "0," (rtos (- zm1 1))) "")
;  (ssadd (entlast) gporet)
;  (command "LINE" (strcat (rtos yn1) "," (rtos (+ zn1 1))) (strcat (rtos ym1) "," (rtos (+ zn1 1))) "")
;  (ssadd (entlast) gporet)
  (setq picad (list 0 (+ zn1 1)))
;  (command "INSERT" "texto2" picad "" "" "")
;  (command "EXPLODE" (entlast))
;  (setq cadt (entlast))
;  (entmod (subst (cons 1 cadtex) (assoc 1 (entget cadt)) (entget cadt)))
  (setq love (- zm1 zn1 2))
  (setq loho (- ym1 yn1 1))
  (setq cuenta 0)
  (setq cuetex septex)
  (setq znn1 zn1)
  (setq zn1 (+ zn1 1))
  (while (<= zn1 zm1)
    (if (= cuetex septex)
      (progn
        (SETQ XYZX (CONS 10 (list (* -1 (+ (* ancho 0.005) ym1)) zn1)))
        (SETQ XYZX2 (CONS 11 (list (* -1 (+ (* ancho 0.005) ym1)) zn1)))
        (SETQ TEXTX (CONS 1 (rtos (+ zn1 0) 2 2)))
        (setq colorcot (cons 62  (atoi ctret)))
        (setq tamanot (cons 40 (atof stret)))
        (setq layert (cons 8 ltret))
        (ENTMAKE (LIST '(0 . "TEXT") '(100 . "AcDbEntity") layert '(100 . "AcDbText") XYZX tamanot TEXTX colorcot '(7 . "ROMANS") '(72 . 2) xyzx2 '(73 . 2)))
        (ssadd (entlast) gporet)
        (SETQ XYZX (CONS 10 (list (+ (* ancho 0.005) yn1) zn1)))
        (SETQ XYZX2 (CONS 11 (list (+ (* ancho 0.005) yn1) zn1)))
        (ENTMAKE (LIST '(0 . "TEXT") '(100 . "AcDbEntity") layert '(100 . "AcDbText") XYZX tamanot TEXTX colorcot '(7 . "ROMANS") '(72 . 0) xyzx2 '(73 . 2)))
        (ssadd (entlast) gporet)
        (setq cuetex 0)
      )
    )
    (setq colorl (cons 62  (atoi cret)))
    (setq valorx (cons 6  "bylayer"))
    (setq punretx (cons 10 (list yn1 (+ zn1 0) 0)))
    (setq punretx2 (cons 11 (list (* ym1 -1) (+ zn1 0) 0)))
    (setq layersec (cons 8 lret))
    (ENTMAKE (LIST '(0 . "LINE") '(100 . "AcDbEntity") layersec valorx '(100 . "AcDbLine") PUNRETX PUNRETX2 colorl))
    (ssadd (entlast) gporet)
    (setq zn1 (+ zn1 sepret))
    (setq cuetex (+ cuetex 1))
    (setq cuenta (+ cuenta 1))
  )
  (setq altosec (* (- cuenta 1) sepret))
  (setq cuenta 0)
  (setq yma (car (cdr (cdr (assoc 10 (entget (entlast)))))))
  (setq cuetex2 septex2)
  (setq yn1 (- yn1 1))
;  (while (> (+ yn1 1) (* (+ sepret ancho) -1))
  (while (>= (+ yn1 1) (* ym1 -1))
;    (setq cuenta (+ cuenta 1))
;    (if (/= yn1 -1)
;      (progn
        (if (= cuetex2 septex2)
          (progn
            (SETQ XYZX (CONS 10 (list (+ yn1 1) (+ znn1 1))))
            (SETQ XYZX2 (CONS 11 (list (+ yn1 1) (+ znn1 0.8))))
            (SETQ TEXTX (CONS 1 (rtos (+ yn1 1) 2 0)))
            (setq colorcot (cons 62  (atoi ctret)))
            (setq tamanot (cons 40 (atof stret)))
            (setq layert (cons 8 capter))
            (ENTMAKE (LIST '(0 . "TEXT") '(100 . "AcDbEntity") layert '(100 . "AcDbText") XYZX tamanot TEXTX colorcot '(7 . "ROMANS") '(72 . 1) xyzx2 '(73 . 3)))
            (ssadd (entlast) gporet)
            (setq cuetex2 0)
          )
        )
        (setq cuetex2 (+ cuetex2 1))
;      )
;    )
    (setq colorl (cons 62  (atoi cret)))
    (setq valorx (cons 6  "bylayer"))
    (setq punretx (cons 10 (list (+ yn1 1) (+ znn1 1) 0)))
    (setq punretx2 (cons 11 (list (+ yn1 1) yma 0)))
    (setq layersec (cons 8 lret))
    (ENTMAKE (LIST '(0 . "LINE") '(100 . "AcDbEntity") layersec valorx '(100 . "AcDbLine") PUNRETX PUNRETX2 colorl))
;    (command "LINE" (strcat (rtos (+ yn1 1)) "," (rtos (+ znn1 1))) (strcat (rtos (+ yn1 1)) "," (rtos yma)) "")
    (ssadd (entlast) gporet)
    (setq yn1 (- yn1 sepret2))
  )
  (setq puninsblo (list yn1 zn1))
  (write-line (strcat (rtos nivel2 2 3) "," cadtexx "," (rtos altosec 2 2)) ArchS)
  (write-line (rtos altosec 2 2))
)


(defun bloque ()
  (command "ERASE" gpoo cad "")
    (setq cadtext nomcad)
    (SETQ LNG (STRLEN nomcad))
    (SETQ NOMBLO "")
    (SETQ CONT 0)
    (REPEAT LNG
        (SETQ CONT (1+ CONT))
        (setq CARACTER (substr CADTEXT CONT 1))
        (IF (= CARACTER "+") (SETQ CARACTER "-"))
        (setq nomblo (STRCAT NOMBLO CARACTER))
    )
  (command "BLOCK" nomblo "0,0" gpoo2 gporet cadt nivv "")  ; GPOX
  (command "VIEW" "R" "C")
)

(defun borrar ()
  (setq r2 (getstring " Eliminar los datos en planta y crear bloque <S>:"))
  (if (= r2 "")
    (setq r2 "S")
  )
  (if (= (strcase r2) "S")
    (bloque)
  )
)

(defun agrega (entagr gpoagr)
  (setq tipagr (cdr (assoc 0 (entget entagr))))
  (setq cueagr 0)
  (while (/= cueagr (sslength gpoagr))
    (setq nomagr (ssname gpoagr cueagr))
    (if (= tipagr (cdr (assoc 0 (entget nomagr))))
      (progn
        (ssdel nomagr gpoagr)
        (setq cueagr (- cueagr 1))
      ) 
    )
    (setq cueagr (+ cueagr 1))
  )
  (ssadd entagr gpoagr)
  (setq agregavar gpoagr)
)


(defun filtro (gpofil)
  (setq cof 0)
  (setq cuelin 0)
  (setq cuetex 0)
  (while (/= cof (sslength gpofil))
    (setq eliobj "SI")
    (setq objfil (ssname gpofil cof))
    (if (= "LINE" (cdr (assoc 0 (entget objfil))))
      (progn
        (setq eliobj "NO")
        (setq cuelin (+ cuelin 1)) 
      ) 
    )
    (if (or (= "pun2" (cdr (assoc 2 (entget objfil)))) (= "PUN2" (cdr (assoc 2 (entget objfil)))))
      (setq eliobj "NO")
    )
    (if (= "TEXT" (cdr (assoc 0 (entget objfil))))
      (progn
        (setq eliobj "NO")
        (setq cuetex (+ cuetex 1)) 
      ) 
    )
    (if (= eliobj "SI")
      (progn
        (ssdel objfil gpofil)
        (setq cof (- cof 1))
      )
    )
    (setq cof (+ cof 1))
  )

  (if (> cuelin 1)
    (progn
      (alert "Se seleccionaron mas de una linea en el grupo")
      (setq tipent "X") 
      (while (/= "LINE" TipEnt)
        (setq lin (car (entsel "Selecciona la linea correspondiente")))
        (setq TipEnt (cdr (assoc 0 (entget lin)))) 
        (if (/= "LINE" TipEnt)
          (alert "La entidad que seleccionaste no es una linea")
        ) 
      ) 
      (setq gpofil (agrega lin gpofil))
    )
  )

  (if (= cuelin 0)
    (progn
      (alert "No se selecciono la linea de la seccion")
      (setq tipent "X") 
      (while (/= "LINE" TipEnt)
        (setq lin (car (entsel "Selecciona la linea correspondiente")))
        (setq TipEnt (cdr (assoc 0 (entget lin)))) 
        (if (/= "LINE" TipEnt)
          (alert "La entidad que seleccionaste no es una linea")
        ) 
      ) 
      (setq gpofil (agrega lin gpofil))
    )
  )

  (if (> cuetex 1)
    (progn
      (alert "Se seleccionaron mas de un texto en el grupo")
      (setq tipent "X") 
      (while (/= "TEXT" TipEnt)
        (setq lin (car (entsel "Selecciona el texto correspondiente (cadenamiento)")))
        (setq TipEnt (cdr (assoc 0 (entget lin)))) 
        (if (/= "TEXT" TipEnt)
          (alert "La entidad que seleccionaste no es un texto")
        ) 
      ) 
      (setq gpofil (agrega lin gpofil))
    )
  )

  (if (= cueTEX 0)
    (progn
      (alert "No se selecciono el texto del cadenamiento")
      (setq tipent "X") 
      (while (/= "TEXT" TipEnt)
        (setq lin (car (entsel "Selecciona el texto correspondiente")))
        (setq TipEnt (cdr (assoc 0 (entget lin)))) 
        (if (/= "TEXT" TipEnt)
          (alert "La entidad que seleccionaste no es un texto")
        ) 
      ) 
      (setq gpofil (agrega lin gpofil))
    )
  )

  (setq filtrovar gpofil)  
)

(defun c:se1 ()
  (setq os (getvar "osmode"))
  (COMMAND "UNDO" "M")
  (command "OSNAP" "none")
  (command "LAYER" "M" "PROV" "")
  (command "LAYER" "M" capten "")
  (command "LAYER" "M" caplir "")
  (command "LAYER" "M" capter "")
  (command "LAYER" "M" capcad "")
  (command "LAYER" "M" capcot "")
  (SETQ ANCHOXXX NIL)
  (setq arch (open (strcat ruta "configuraciones de programas\\ConfiSec.txt") "r"))
  (setq lfont (read-line arch))
  (close arch)
  (setq haydat "Y")

  (if (not NomArcs)
    (setq haydat nil)
  )
  (if (not ancho)
    (setq haydat nil)
  )
  (if (not sepret)
    (setq haydat nil)
  )
  (if (not sepret2)
    (setq haydat nil)
  )
  (if (not septex)
    (setq haydat nil)
  )
  (if (not septex2)
    (setq haydat nil)
  )
  (if (= haydat nil)
    (progn
    (setq valida nil)
    (while (= valida nil)
      (setq arccon nil)
      (while (= arccon nil)
        (setq arccon (open (strcat ruta "configuraciones de programas\\ConfiSec.txt") "r"))
        (if (= arccon nil)
          (progn
            (alert "No existe el archivo de configuracion del programa; se pediran los datos para crearlo ")
            (C:CreaCFG)
          )
        )
      )
      (write-line "Leeo datos de configuracion")
      (setq ancho (atof (substr (read-line arccon) 25)))
      (setq ancho (/ ancho 2))
      (setq sepret (atof (substr (read-line arccon) 28)))
      (setq septex (atof (substr (read-line arccon) 28)))
      (setq sepret2 (atof (substr (read-line arccon) 28)))
      (setq septex2 (atof (substr (read-line arccon) 28)))
      (setq NomArcS (substr (read-line arccon) 28))
      (setq CapTeN (substr (read-line arccon) 18))
      (setq CapLiR (substr (read-line arccon) 24))
      (setq CapTeR (substr (read-line arccon) 24))
      (setq CapCad (substr (read-line arccon) 18))
      (setq CapCot (substr (read-line arccon) 10))
      (setq escalacad (substr (read-line arccon) 20))
      (setq stret (substr (read-line arccon) 20))

      (setq valida "V")
      (if (= ancho 0)
        (setq valida nil)
      )
     (if (= sepret 0)
        (setq valida nil)
      )
      (if (= sepret2 0)
        (setq valida nil)
      )
      (if (= septex 0)
        (setq valida nil)
      )
      (if (= septex2 0)
        (setq valida nil)
      )
      (if (= NomArcS "")
        (setq valida nil)
      )
      (if (= CapTeN "")
        (setq valida nil)
      )
      (if (= CapLiR "")
        (setq valida nil)
      )
      (if (= CapTeR "")
        (setq valida nil)
      )
      (if (= CapCad "")
        (setq valida nil)
      )
      (if (= CapCot "")
        (setq valida nil)
      )
      (if (= escalacad "")
        (setq valida nil)
      )
      (if (= stret "")
        (setq valida nil)
      )
      (if (= valida nil)
        (C:CreaCFG)
      )
    (command "-layer" "N" CAPTEN "C" "GREEN" CAPTEN
    "N" CAPLIR "C" "YELLOW" CAPLIR 
    "N" CAPTER
    "N" CAPCAD
    "N" "PROV"
    "N" CAPCOT "")
    )
    )
  )
  (setq ArchS (open NomArcs "a"))
  (print "\n Seleciona los elementos a procesar ")
  (command "VIEW" "S" "C")
  (setq gpo (ssget))
  (setq gpo (filtro gpo))
  (setq eleme (sslength gpo))
  (setq gpoo (ssadd))
  (ordena)
  (setq nomcad (cdr (assoc 1 (entget cad))))
  (mueve)
  (rota)
  (setq contadprv 0)
  (setq ex (ssname gpoo contadprv))
  (while ex
    (setq xm (car (cdr (assoc 10 (entget ex)))))
    (IF (= ANCHOXXX NIL) (setq anchoxxx xm))
    (IF (= ANCHOXXX1 NIL) (setq anchoxxx1 xm))
    (IF (< ANCHOXXX xm) (setq anchoxxx xm))
    (IF (> ANCHOXXX1 xm) (setq anchoxxx1 xm))
    (setq contadprv (1+ contadprv))
    (setq ex (ssname gpoo contadprv))
  )
  (setq eleme (- eleme 1))
  (setq gpo gpoo)
  (ordena2)
  (traza)
  (ver1)
  (inserta)
  (reticula)
   (COMMAND "ERASE" GPOO2 "")
   (setq gpoO2 (ssADD))
   (ssadd POLIL gpoo2)
  (borrar)
  (close archs)
  (setvar "osmode" os)
)

(defun c:RESE ()
  (setq ancho nil)
  (setq sepret nil)
  (setq sepret2 nil)
  (setq septex nil)
  (setq septex2 nil)
  (setq NomArcs nil)
  (write-line "Valores Reinicializados de secciones")
)

(defun cottopo (numero)
   (setq nombre (rtos numero 2 3))
   (setq nombre (rtos (/ (atof nombre) 1000) 2 7))
    (SETQ LNG (STRLEN NOMBRE))
    (SETQ NOMBLO "")
    (SETQ CONT 0)
    (REPEAT LNG
        (SETQ CONT (1+ CONT))
        (setq CARACTER (substr NOMBRE CONT 1))
        (IF (= CARACTER ".") (SETQ CARACTER "+"))
        (setq nomblo (STRCAT NOMBLO CARACTER))
    )
  (setq nomblo (strcat (substr nomblo 1 (- lng 4)) "." (substr nomblo (- lng 3) 3)))
  (setq lng (1+ lng))
  (if (= (substr nomblo (- lng 3) 3) "000") (setq nomblo (substr nomblo 1 (- lng 5))))
  (setq nuetex nomblo)
)

(defun DatC (linea nudato)
  (setq cuen 0)
  (setq cuecom 0)
  (setq salir "N")
  (setq cadena "")
  (while (/= salir "S")
    (setq cuen (+ cuen 1))
    (setq caracter (substr linea cuen 1))
    (if (= caracter ",")
      (setq cuecom (+ cuecom 1))
    )
    (if (= cuecom (- nudato 1))
      (if (/= caracter ",")
        (setq cadena (strcat cadena caracter))
      )
    )
    (if (or (= cuecom nudato) (>= cuen (strlen linea)))
      (setq salir "S")
    )
  )
  (setq cadena cadena)
)

(defun c:DESSEC ()
  (setq altura "83")
  (setq sver "0.1")
  (setq shor "0.1")
  (setq opcion "n")
  (setq dcl_id (load_dialog (strcat ruta "dialogos\\DESSEC.dcl"))) ; Load the DCL file.
  (if (not (new_dialog "DESSEC" dcl_id))   ; Initialize the dialog.
    (exit)                                ; Exit if this doesn't 
                                          ; work.
  )
  (set_TILE "altura" altura)
  (set_TILE "sver" sver)
  (set_TILE "shor" shor)
  (action_tile "altura" "(var3)")
  (action_tile "sver" "(var3)")
  (action_tile "shor" "(var3)")
  (action_tile "actualiza" "(dibujo2)")
  (action_tile "accept" "(insertas)")
  (start_dialog)                          ; Display the dialog 
                                          ; box.
  (unload_dialog dcl_id)                  ; Unload the DCL file.
  (princ)
  (if (= opcion "s") 
    (continue)
  )
)

(defun insertas ()
  (setq opcion "s")
  (done_dialog)
)

(defun continue ()
  (C:LIBRERIA "busca block en base de datos")
  (C:LIBRERIA "ZOOM ULTIMO OBJETO INSERTADO")
  (COMMAND "LUNITS" 2)
  (COMMAND "LUPREC" 7)
  (COMMAND "AUNITS" 0)
  (COMMAND "AUPREC" 4)
  (COMMAND "ANGDIR" 0)
  (COMMAND "ANGBASE" 0.0)
  (COMMAND "DIMZIN" 0)
  (SETQ CADENX NIL)
  (SETQ PYINI "")
  (SETQ PY "")
  (SETQ OPCIONESOS (GETVAR "OSMODE"))
  (command "osnap" "none")
  (SETQ CADEN 0)
  (IF (= COMPLEMENTO NIL)(SETQ COMPLEMENTO ""))
  (SETQ SBLOCK (SBLBD (STRCAT "0-000" COMPLEMENTO)))
  (IF (/= SBLOCK "S") (progn (SETQ CADENX (GETREAL "\n El inicio no fue encontrado con que cadenamiento inicia :")) (SETQ CADEN CADENX)))
  (if (= CADENX NIL) (SETQ CADENX 0))
  (setq salida "n")
  (WHILE salida
    (SETQ caden (1+ caden))
    (setq caden2 (cottopo caden))
    (setq caden2 (cadnum2 caden2))
    (SETQ SBLOCK (SBLBD (STRCAT caden2 COMPLEMENTO)))
    (if (= sblock "S") (setq salida nil))
  )
  (setq salida "n")
  (setq intervalo (- CADEN CADENX))
  (SETQ CADEN (- CADEN (* INTERVALO 2)))
  (setq busc (strcase (getstring "\n Buscar secciones intermedias entre secciones (S/N) <S>")))
  (SETQ PINI (GETPOINT "\n DAME EL PUNTO BASE DE INSERCION DE LAS SECCIONES"))
  (SETQ PX (CAR PINI))
  (SETQ PY (CADR PINI))
  (SETQ PYINI PY)
  (SETQ XMAXIMA PX)
  (if (= busc "N")
   (progn
    (WHILE salida
      (SETQ caden (+ intervalo caden))
      (setq caden2 (cottopo caden))
      (setq caden2 (cadnum2 caden2))
      (SETQ SBLOCK (SBLBD (STRCAT caden2 COMPLEMENTO)))
      (if (/= sblock "S") 
         (PROGN
           (setq salida nil) 
         )
         (PROGN
;           (SETQ CADEN2 (STRCAT CADEN2 "A"))
           (COMMAND "INSERT" (STRCAT caden2 COMPLEMENTO) "0,0" "" "" "") 
           (ZBLOCK)
           (COMMAND "ERASE" (SSGET "P") "")
           (IF (> (- PYINI (- PY (- YUMAX YDMAX))) (ATOF ALTURA))
              (PROGN
                (SETQ PY PYINI)
                (SETQ PX (+ XMAXIMA (ATOF SVER)))
              )
           )
           (COMMAND "INSERT" (STRCAT caden2 COMPLEMENTO) (STRCAT (RTOS (+ PX XDMAX)) "," (RTOS (- PY YuMAX))) "" "" "")    
           (IF (> (+ PX (* 2 XDMAX)) XMAXIMA) (SETQ XMAXIMA (+ PX (* 2 XDMAX))))
           (SETQ PY (- PY (ATOF SHOR) (- YUMAX YDMAX)))
         )
      )
    )
   )
   (progn
    (WHILE salida
       (setq salida2 "n")
       (setq contador 0)
       (WHILE salida2
         (SETQ caden (1+ caden))
          (setq contador (1+ contador))
          (if (> contador 1000) (progn (setq salida nil) (setq salida2 nil)))
          (setq caden2 (cottopo caden))
          (setq caden2 (cadnum2 caden2))
          (SETQ SBLOCK (SBLBD (STRCAT caden2 COMPLEMENTO)))
         (if (= sblock "S") (setq salida2 nil))
        )
           (COMMAND "INSERT" (STRCAT caden2 COMPLEMENTO) "0,0" "" "" "") 
           (ZBLOCK)
           (COMMAND "ERASE" (SSGET "P") "")
           (IF (> (- PYINI (- PY (- YUMAX YDMAX))) (ATOF ALTURA))
              (PROGN
                (SETQ PY PYINI)
                (SETQ PX (+ XMAXIMA (ATOF SVER)))
              )
           )
           (COMMAND "INSERT" (STRCAT caden2 COMPLEMENTO) (STRCAT (RTOS (+ PX XDMAX)) "," (RTOS (- PY YuMAX))) "" "" "")    
           (IF (> (+ PX (* 2 XDMAX)) XMAXIMA) (SETQ XMAXIMA (+ PX (* 2 XDMAX))))
           (SETQ PY (- PY (ATOF SHOR) (- YUMAX YDMAX)))
    )
   );PROGN
  );IF
  (prompt caden2)
  (SETVAR "OSMODE" OPCIONESOS)
)
