(defun C:ARREGL ()
    (setq RC (getSTRING " RECTANGULAR O POLAR (R/P): <R>"))
    (setq linea (car (entsel "Selecciona la linea donde comenzar: ")))
    (IF (= RC "")
      (SETQ RC "R")
    )
    (IF (= (strcase RC) "R")
     (PROGN
      (setq pun (getpoint "PUNTO DE INICIO : "))
      (setq pun2 (getpoint "FIN : "))
      (setq ancho (getreal "Ancho de los lotes : "))
      (setq a (angle pun pun2))
      (setq a (* 180 (/ a pi)))
      (command "snap" "ro" pun a)
      (command "snap" "off")
      (setq ds (distance pun pun2))
      (setq f (/ ds ancho))
      (setq f (FIX F))
      (setq f (1+ F))
      (command "array" linea "" "R" "" F ancho)
     )
     (PROGN
      (setq pun (getpoint "ANGULO DE INICIO : "))
      (setq pun2 (getpoint "ANGULO FINAL : "))
      (setq pun3 (getpoint "PUNTO CENTRAL : "))
      (setq anG (getreal "Angulo de los LINEAS : "))
      (setq a (angle pun pun2))
      (setq a (* 180 (/ a pi)))
      (setq f (/ A ANG))
      (setq f (FIX F))
      (setq f (1+ F))
      (COMMAND "ARRAY" LINEA "" "P" PUN3 F A "")
     )
    )
    (command "snap" "ro" "0,0" "0")
    (command "snap" "off")
)
