(defun c:CRP ()
  (C:LIBRERIA "AREA OBTENIDA EN UN PUNTO")
  (C:LIBRERIA "BUSCA LAYER EN BASE DE DATOS")
  (COMMAND "LUNITS" 2)
  (COMMAND "LUPREC" 7)
  (COMMAND "AUNITS" 0)
  (COMMAND "AUPREC" 4)
  (COMMAND "ANGDIR" 0)
  (COMMAND "ANGBASE" 0.0)
  (COMMAND "DIMZIN" 0)
  (setq cdrive (substr ruta 1 1))
  (setq os (getvar "osmode"))
  (COMMAND "UNDO" "M")
  (command "OSNAP" "none")
  (SETQ GPOBLK (SSADD))
  (SETQ OPPRV (BSLAYER "PROYECTO"))
  (IF (/= OPPRV "S") (COMMAND "LAYER" "M" "PROYECTO" "C" "RED" "" ""))
  (COMMAND "LAYER" "S" "PROYECTO" "")
;  (SETQ CADENAMIENTO (GETSTRING "\n CADENAMIENTO (VALOR DE CADENA) :"))
    (setq texto (car (entsel "Selecciona el texto DE CADENAMIENTO : ")))
    (setq CADENAMIENTO (cdr (assoc 1 (entget TEXTO))))
   (COMMAND "CHANGE" TEXTO "" "P" "C" "RED" "")
;  (SETQ ELEVPRV (GETREAL "\n ELEVACION DE PROYECTO :"))
    (setq texto (car (entsel "Selecciona el texto DE ELEVACION : ")))
    (setq ELEVPRV (ATOF (cdr (assoc 1 (entget TEXTO)))))
    (SETQ ELEVPRV (+ ELEVPRV 0.55))
   (COMMAND "CHANGE" TEXTO "" "P" "C" "RED" "")
;  (SETQ PENDIENTE (GETREAL "\n DAME LA PENDIENTE DEL PROYECTO (1.00 = 100%) :"))
    (setq texto (car (entsel "Selecciona el texto DE PENDIENTE : ")))
    (setq PENDIENTE (ATOF (cdr (assoc 1 (entget TEXTO)))))
    (IF (= (cdr (assoc 1 (entget TEXTO))) "-2")
      (PROGN
        (command "INSERT" (strcat ruta "BLOCKS\\ST.dwg") (STRCAT "0," (RTOS ELEVPRV 2 6)) "" "" "")
        (COMMAND "EXPLODE" (ENTLAST) "")
        (SETQ GPOL (SSGET "P"))
        (SETQ PROVY 0)
        (SETQ EX (SSNAME GPOL 0))
        (WHILE EX
          (SSADD EX GPOBLK)
          (SETQ PROVY (1+ PROVY))
          (SETQ EX (SSNAME GPOL PROVY))
        )
        (command "INSERT" (strcat ruta "BLOCKS\\TEXTO1.dwg") (STRCAT "0," (RTOS ELEVPRV 2 6)) "" "" "")
        (command "EXPLODE" (entlast))
        (setq TEXTO (entlast))
        (COMMAND "CHANGE" texto "" "" "" "" "" "" (STRCAT "RASANTE = " (RTOS ELEVPRV 2 3)))
        (SSADD TEXTO GPOBLK)
        (command "INSERT" (strcat ruta "BLOCKS\\TEXTO2.dwg") (STRCAT "0," (RTOS ELEVPRV 2 6)) "" "" "")
        (command "EXPLODE" (entlast))
        (setq TEXTO (entlast))
        (COMMAND "CHANGE" texto "" "" "" "" "" "" CADENAMIENTO)
        (SSADD TEXTO GPOBLK)
        (setvar "osmode" os)
        (COMMAND "ZOOM" "C" (STRCAT "0," (RTOS ELEVPRV 2 3)) "12")
        (GETSTRING "PRESIONA CUALQUIER TECLA PARA CONTINUAR")
        (COMMAND "BLOCK" (STRCAT CADENAMIENTO "P") "0,0" GPOBLK "" "")
        (COMMAND "ZOOM" "P" "")
        (FINISH)
      )
    )
   (COMMAND "CHANGE" TEXTO "" "P" "C" "RED" "")
   (SETQ PENDIENTE (/ PENDIENTE 100))
;  (SETQ ANCHOI (GETREAL "\n ANCHO DEL PROYECTO DEL LADO IZQUIERDO :"))
    (setq texto (car (entsel "Selecciona el texto DE LONGUITUD DEL LADO IZQUIERDO : ")))
    (setq ANCHOI (ATOF (cdr (assoc 1 (entget TEXTO)))))
   (COMMAND "CHANGE" TEXTO "" "P" "C" "RED" "")
   (SETQ ANCHOI (- ANCHOI 1))
;  (SETQ ANCHOD (GETREAL "\n ANCHO DEL PROYECTO DEL LADO DERECHO :"))
    (setq texto (car (entsel "Selecciona el texto DE LONGUITUD DEL LADO DERECHO : ")))
    (setq ANCHOD (ATOF (cdr (assoc 1 (entget TEXTO)))))
   (COMMAND "CHANGE" TEXTO "" "P" "C" "RED" "")
   (SETQ ANCHOD (- ANCHOD 1))
  (IF (> ANCHOI ANCHOD)
    (COMMAND "ZOOM" "C" (STRCAT "0," (RTOS ELEVPRV 2 3)) (* ANCHOI 4.5))
  )
  (IF (< ANCHOI ANCHOD)
    (COMMAND "ZOOM" "C" (STRCAT "0," (RTOS ELEVPRV 2 3)) (* ANCHOD 4.5))
  )
  (IF (= ANCHOI ANCHOD)
    (COMMAND "ZOOM" "C" (STRCAT "0," (RTOS ELEVPRV 2 3)) (* ANCHOD 3))
  )
  (IF (< ANCHOI ANCHOD)
    (SETQ PENDIENTE (* PENDIENTE -1)) 
  )
  (SETQ Y1 (- ELEVPRV (* ANCHOI PENDIENTE)))
  (SETQ Y2 (+ ELEVPRV (* ANCHOD PENDIENTE)))

  (setq x1 (* ANCHOI -1))
;  (setq y1 (car (cdr pun1)))
  (setq x2 ANCHOD)
;  (setq y2 (car (cdr pun2)))
  (setq xd (- x1 x2))
  (if (> 0 xd)
    (setq xd (* xd -1))
  )
  (setq xd (/ xd 2))

  (setq yd (- y1 y2))
  (if (> 0 yd)
    (setq yd (* yd -1))
  )
  (setq yd (/ yd 2))
  (if (> x1 x2)
    (setq xd (+ xd x2))
    (setq xd (+ xd x1))
  )
  (if (> y1 y2)
    (setq yd (+ yd y2))
    (setq yd (+ yd y1))
  )
  (setq punmid (list xd yd))  
  (SETQ YM (- Y1 Y2))
  (SETQ XM (- X1 X2))
  (SETQ M (/ YM XM))
  (IF (> M 0) (SETQ SIGNO "+") (SETQ SIGNO ""))
  (SETQ M (RTOS (* 100 M) 2 1))
  (SETQ M (STRCAT SIGNO M " %"))
;  (if (> X1 X2) 
    (SETQ ORR (list x2 y2))
;  )
  (SETQ PUNMID2 (SUMA PUNMID 0.2 0.2))
  (SETQ ORR (SUMA ORR 0.2 0.2))
  (COMMAND "INSERT" (STRCAT RUTA "BLOCKS\\TEXTC") PUNMID2 "0.25" "" ORR)
  (COMMAND "EXPLODE" "L" "")
  (COMMAND "CHANGE" "L" "" "" "" "" "" "" M)
  (SSADD (ENTLAST) GPOBLK)
  (setq xP1 (* ANCHOI -1))
;  (setq yP1 (car (cdr pun1)))
  (setq xP2 XD)
  (setq yP2 YD)
  (setq xd (- xP1 xP2))
  (if (> 0 xd)
    (setq xd (* xd -1))
  )
  (setq xd (/ xd 2))

  (setq yd (- y1 yP2))
  (if (> 0 yd)
    (setq yd (* yd -1))
  )
  (setq yd (/ yd 2))
  (if (> xP1 xP2)
    (setq xd (+ xd xP2))
    (setq xd (+ xd xP1))
  )
  (if (> y1 y2)
    (setq yd (+ yd yP2))
    (setq yd (+ yd y1))
  )
  (setq punmid3 (list xd yd))  
  (SETQ PUNMID2 (SUMA PUNMID3 0.2 0.2))
  (COMMAND "INSERT" (STRCAT RUTA "BLOCKS\\TEXTC") PUNMID2 "0.25" "" ORR)
  (COMMAND "EXPLODE" "L" "")
  (COMMAND "CHANGE" "L" "" "" "" "" "" "" (RTOS ANCHOI 2 3))
  (SSADD (ENTLAST) GPOBLK)
  (setq xP1 XP2)
  (setq yP1 YP2)
  (setq xP2 X2)
  (setq yP2 Y2)
  (setq xd (- xP1 xP2))
  (if (> 0 xd)
    (setq xd (* xd -1))
  )
  (setq xd (/ xd 2))

  (setq yd (- yP1 yP2))
  (if (> 0 yd)
    (setq yd (* yd -1))
  )
  (setq yd (/ yd 2))
  (if (> xP1 xP2)
    (setq xd (+ xd xP2))
    (setq xd (+ xd xP1))
  )
  (if (> yP1 yP2)
    (setq yd (+ yd yP2))
    (setq yd (+ yd yP1))
  )
  (setq punmid3 (list xd yd))  
  (SETQ PUNMID2 (SUMA PUNMID3 0.2 0.2))
  (COMMAND "INSERT" (STRCAT RUTA "BLOCKS\\TEXTC") PUNMID2 "0.25" "" ORR)
  (COMMAND "EXPLODE" "L" "")
  (COMMAND "CHANGE" "L" "" "" "" "" "" "" (RTOS ANCHOD 2 3))
  (SSADD (ENTLAST) GPOBLK)

  (COMMAND "LINE" (STRCAT (RTOS (* ANCHOI -1) 2 6) "," (RTOS Y1 2 6)) (STRCAT (RTOS ANCHOD 2 6) "," (RTOS Y2 2 6)) "")
  (SETQ LIN (ENTLAST))
  (SSADD LIN GPOBLK)
  (COMMAND "COPY" LIN "" (STRCAT "0," (RTOS ELEVPRV 2 3)) (STRCAT "0," (RTOS (- ELEVPRV 0.05) 2 3)))
  (COMMAND "SCALE" (ENTLAST) "" (STRCAT "0," (RTOS (- ELEVPRV 0.05) 2 3)) "1.5")
  (SETQ LIN2 (ENTLAST))
  (SSADD LIN2 GPOBLK)
  (COMMAND "COPY" LIN "" (STRCAT "0," (RTOS ELEVPRV 2 3)) (STRCAT "0," (RTOS (- ELEVPRV 0.25) 2 3)))
  (COMMAND "SCALE" (ENTLAST) "" (STRCAT "0," (RTOS (- ELEVPRV 0.25) 2 3)) "1.5")
  (SETQ LIN3 (ENTLAST))
  (SSADD LIN3 GPOBLK)
  (COMMAND "COPY" LIN "" (STRCAT "0," (RTOS ELEVPRV 2 3)) (STRCAT "0," (RTOS (- ELEVPRV 0.55) 2 3)))
  (COMMAND "SCALE" (ENTLAST) "" (STRCAT "0," (RTOS (- ELEVPRV 0.55) 2 3)) "1.5")
  (SETQ LIN4 (ENTLAST))
  (SSADD LIN4 GPOBLK)
  (command "insert" (strcat ruta "BLOCKS\\TALUDI.dwg") (STRCAT (RTOS (* ANCHOI -1) 2 6) "," (RTOS Y1 2 6)) "" "" "")
  (COMMAND "EXPLODE" (ENTLAST) "")
  (SETQ GPOPROV (SSGET "P"))
;  (IF (= (cdr (assoc 0 (entget (ssname gpoPROV 0)))) "LWPOLYLINE")
    (SETQ ETR1 (SSNAME GPOPROV 2))
;    (SETQ ETR2 (SSNAME GPOPROV 1))
;    (SETQ ETR2 (SSNAME GPOPROV 1))
;  )
  (SSADD (SSNAME GPOPROV 0) GPOBLK)
  (SSADD (SSNAME GPOPROV 1) GPOBLK)
  (SSADD (SSNAME GPOPROV 2) GPOBLK)
  (command "insert" (strcat ruta "BLOCKS\\TALUDD.dwg") (STRCAT (RTOS ANCHOD 2 6) "," (RTOS Y2 2 6)) "" "" "")
  (COMMAND "EXPLODE" (ENTLAST) "")
  (SETQ GPOPROV (SSGET "P"))
;  (IF (= (cdr (assoc 0 (entget (ssname gpoPROV 0)))) "LWPOLYLINE")
    (SETQ ETR2 (SSNAME GPOPROV 2))
;    (SETQ ETR2 (SSNAME GPOPROV 0))
;  )
  (SSADD (SSNAME GPOPROV 0) GPOBLK)
  (SSADD (SSNAME GPOPROV 1) GPOBLK)
  (SSADD (SSNAME GPOPROV 2) GPOBLK)
  (command "INSERT" (strcat ruta "BLOCKS\\TEXTO1.dwg") (STRCAT "0," (RTOS ELEVPRV 2 6)) "" "" "")
  (command "EXPLODE" (entlast))
  (setq TEXTO (entlast))
  (COMMAND "CHANGE" texto "" "" "" "" "" "" (STRCAT "RASANTE = " (RTOS ELEVPRV 2 3)))
  (SSADD TEXTO GPOBLK)
  (command "INSERT" (strcat ruta "BLOCKS\\TEXTO2.dwg") (STRCAT "0," (RTOS ELEVPRV 2 6)) "" "" "")
  (command "EXPLODE" (entlast))
  (setq TEXTO (entlast))
  (COMMAND "CHANGE" texto "" "" "" "" "" "" CADENAMIENTO)
  (SSADD TEXTO GPOBLK)
  (setq XYZ (cdr (assoc 10 (entget lin2)))) 
  (setq XYZ2 (cdr (assoc 10 (entget lin3)))) 
  (setq XYZ3 (cdr (assoc 10 (entget lin4)))) 
  (COMMAND "TRIM" ETR1 "" XYZ XYZ2 XYZ3 "")
  (setq XYZ (cdr (assoc 11 (entget lin2)))) 
  (setq XYZ2 (cdr (assoc 11 (entget lin3)))) 
  (setq XYZ3 (cdr (assoc 11 (entget lin4)))) 
  (COMMAND "TRIM" ETR2 "" XYZ XYZ2 XYZ3 "")
  (SETQ XYZ (STRCAT "0," (RTOS (- ELEVPRV 0.025) 2 3)))
  (SETQ XYZ2 (STRCAT "0," (RTOS (- ELEVPRV 0.15) 2 3)))
  (SETQ XYZ3 (STRCAT "0," (RTOS (- ELEVPRV 0.35) 2 3)))
;  (SETQ ACA (AREAP XYZ ARP))
;  (SETQ ABH (AREAP XYZ2 ARP))
;  (SETQ ASR (AREAP XYZ3 ARP))
;  (command "INSERT" (strcat ruta "BLOCKS\\AREASCHON.dwg") PAUSE "" "" "" "" "" "" "" "" "" "" "" "" "" "" "" "" "" "" "" "" "" "" "" "" "" "")
;  (SSADD (ENTLAST) GPOBLK)
;  (setq bl (entnext (ENTLAST)))
;  (COMMAND "attedit" "" "" "" "" bl "V" "R" CADENAMIENTO "")
;  (setq bl (entnext BL))
;  (COMMAND "attedit" "" "" "" "" bl "V" "R" ELEVPRV "")
;  (setq bl (entnext BL))
;  (setq bl (entnext BL))
;  (setq bl (entnext BL))
;  (setq bl (entnext BL))
;  (setq bl (entnext BL))
;  (setq bl (entnext BL))
;  (COMMAND "attedit" "" "" "" "" bl "V" "R" ASR "")
;  (setq bl (entnext BL))
;  (COMMAND "attedit" "" "" "" "" bl "V" "R" ABH "")
;  (setq bl (entnext BL))
;  (COMMAND "attedit" "" "" "" "" bl "V" "R" ACA "")
  (setvar "osmode" os)
  (COMMAND "BLOCK" (STRCAT CADENAMIENTO "P") "0,0" GPOBLK "" "")
  (COMMAND "ZOOM" "P" "")
)

(defun SUMA (punto xx yy)
  (setq x (car punto))
  (setq y (car (cdr punto)))
  (setq xxx (+ x xx))
  (setq yyy (+ y yy))
  (list xxx yyy)
)
