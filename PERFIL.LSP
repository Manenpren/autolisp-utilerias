(command "osnap" "none")

(defun SUMA (punto xx yy)
  (setq x (car punto))
  (setq y (car (cdr punto)))
  (setq xxx (+ x xx))
  (setq yyy (+ y yy))
  (list xxx yyy)
)

(defun DatC (linea nudato)
  (setq cuen 0)
  (setq cuecom 0)
  (setq salir "N")
  (setq cadena "")
  (while (/= salir "S")
    (setq cuen (+ cuen 1))
    (setq caracter (substr linea cuen 1))
    (if (= caracter ",")
      (setq cuecom (+ cuecom 1))
    )
    (if (= cuecom (- nudato 1))
      (if (/= caracter ",")
        (setq cadena (strcat cadena caracter))
      )
    )
    (if (or (= cuecom nudato) (>= cuen (strlen linea)))
      (setq salir "S")
    )
  )
  (setq cadena cadena)
)

(defun entero (numed)
  (setq numed (rtos numed 2 8))
  (setq cuecar 1)
  (setq letra "")
  (while (/= letra ".")
    (setq letra (substr numed cuecar 1))
    (setq cuecar (+ cuecar 1))
    (if (= letra "")
      (setq letra ".")
    )
  )
  (setq frac (atof (substr numed 1 (- cuecar 1))))
)

(defun fraccion (numed)
  (setq numed (rtos numed 2 8))
  (setq cuecar 1)
  (setq letra "")
  (while (/= letra ".")
    (setq letra (substr numed cuecar 1))
    (setq cuecar (+ cuecar 1))
    (if (= letra "")
      (setq letra ".")
    )
  )
  (setq frac (atof (substr numed (- cuecar 1))))
)

(defun AMinSec (angull)
  (setq min2 (* (fraccion angull) 60))
  (setq min (rtos (entero (* (fraccion angull) 60)) 2 0))
  (setq sec (rtos (* (fraccion min2) 60) 2 0))
  (if (> 0 angull)
    (setq angull (* angull -1))
  )
  (setq angres (strcat (rtos (entero angull) 2 0) "%%d" min "'" sec "''"))
)


(defun cottop (NUMERO)
   (setq texto (rtos numero 2 3))
   (setq kilm 0)
   (if (= numero 0)
     (setq resto "000")
   )
   (if (> numero 0)
     (setq resto (strcat "00" texto))
   )
   (if (> numero 9)
     (setq resto (strcat "0" texto))
   )
   (if (> numero 99)
     (setq resto texto)
   )
   (if (> numero 999)
    (progn
      (setq num1 (substr texto 1 1))
      (setq resto (substr texto 2 3))
    )
    (setq num1 "0")
   )
   (if (> numero 9999)
    (progn
      (setq num1 (substr texto 1 2))
      (setq resto (substr texto 3 3))
    )
  )
  (setq nuetex (strcat num1 "+" resto))
)

(defun vertice (poli nov)
  (setq listap (entget poli))
  (setq nver 0)
  (setq salir "N")
  (while (= salir "N")
    (setq sublisp (car listap))
    (if (= 10 (car sublisp))
      (progn
        (setq punto (cdr sublisp))   
        (setq nver (+ nver 1))
      )
    )
    (setq listap (cdr listap))
    (if listap
      (setq salir "N")
      (setq salir "S")
    )
    (if (= nov nver)
      (setq salir "S")
    )
  )
  (if (not listap)
    (setq punto nil)
  )
  (setq punto punto)
)

(defun c:perfil ()
  (command "LAYER" "M" "PERFIL" "")
  (command "LAYER" "M" "RETICULA" "")
  (command "LAYER" "C" "1" "RETICULA" "")
  (command "LAYER" "S" "PERFIL" "")
  (setq polper (car (entsel "Selecciona la polylinea del perfil: ")))
  (setq nomblo (substr (getstring "Nombre del bloque a utilizar: ") 1 6))
  (setq exagera (getreal "Exageración vertical: "))
  (setq posatr (getint " Posición del atributo para elevación: "))
  (setq posatr2 (getint " Posicion del atributo de identificacion: "))
  (setq sepret (getint " Separacion de la reticula: "))

  (setq cuenta 1)
  (setq vez 0)
  (setq dis 0)
  (setq disac 0)
  (command "VIEW" "S" "HOLA")
  (setq elevma -100)
  (setq elevme 999999)

  (while (vertice polper cuenta)
    (setq PunverA PunVer)
    (setq punver (vertice polper cuenta))
    (setq punver1 (suma punver -0.1 -0.1))
    (setq punver2 (suma punver 0.1 0.1))
    (command "ZOOM" "W" punver1 punver2)
    (setq GpoPun (ssget "C" punver1 punver2))
    (setq ElevA Elev)
    (setq DisA DisAc)
    (setq cuenta2 0)
    (while (/= cuenta2 (sslength GpoPun))
      (setq nomobj (ssname gpopun cuenta2))
      (if (= "INSERT" (cdr (assoc 0 (entget nomobj))))
      (progn
      (if (= (substr (cdr (assoc 2 (entget nomobj))) 1 6) nomblo)
        (progn
          (setq atr 0)
          (setq oelev nomobj)
          (while  (/= posatr atr)
            (setq oelev (entnext oelev))
            (setq atr (+ atr 1))
          )
          (setq elev (cdr (assoc 1 (entget oelev))))
          (setq elev (rtos (atof elev) 2 3))

          (setq atr 0)
          (setq oelev nomobj)
          (while  (/= posatr2 atr)
            (setq oelev (entnext oelev))
            (setq atr (+ atr 1))
          )
          (setq identifi (cdr (assoc 1 (entget oelev))))

        )
      )
      )
      )
      (setq cuenta2 (+ cuenta2 1))
    )
    (setq cuenta (+ cuenta 1))
    (setq vez 1)
    (if (> (atof elev) elevma)
      (setq elevma (atof elev))  
    )
    (if (< (atof elev) elevme)
      (setq elevme (atof elev))  
    )
  )
  (setq elevmin (* (getreal (strcat "Elevación mínima: " (rtos elevme 2 3) " :")) exagera))
  (setq elevmax (* (getreal (strcat "Elevación maxima: " (rtos elevma 2 3) " :")) exagera))

  (setq cuenta 1)
  (setq vez 0)
  (setq dis 0)
  (setq disac 0)
  (command "VIEW" "S" "HOLA")
  (while (vertice polper cuenta)
    (setq PunverA PunVer)
    (setq punver (vertice polper cuenta))
    (setq punver1 (suma punver -0.1 -0.1))
    (setq punver2 (suma punver 0.1 0.1))
    (command "ZOOM" "W" punver1 punver2)
    (setq GpoPun (ssget "C" punver1 punver2))
    (setq ElevA Elev)
    (setq DisA DisAc)
    (setq cuenta2 0)
    (while (/= cuenta2 (sslength GpoPun))
      (setq nomobj (ssname gpopun cuenta2))
      (if (= "INSERT" (cdr (assoc 0 (entget nomobj))))
      (progn
      (if (= (substr (cdr (assoc 2 (entget nomobj))) 1 6) nomblo)
        (progn
          (setq atr 0)
          (setq oelev nomobj)
          (while  (/= posatr atr)
            (setq oelev (entnext oelev))
            (setq atr (+ atr 1))
          )
          (setq elev (cdr (assoc 1 (entget oelev))))
          (setq elev (rtos (atof elev) 2 3))

          (setq atr 0)
          (setq oelev nomobj)
          (while  (/= posatr2 atr)
            (setq oelev (entnext oelev))
            (setq atr (+ atr 1))
          )
          (setq identifi (cdr (assoc 1 (entget oelev))))

        )
      )
      )
      )
      (setq cuenta2 (+ cuenta2 1))
    )
    (if (= vez 0)
      (progn
        (setq PunTex (list 0 (- elevmin 15)))
        (setq TEXTOPER (rtos 0 2 3))
        (setq texto1 "0+000.000")
        (command "INSERT" (STRCAT RUTA "BLOCKS\\TEXTOPER") PunTex "3" "3" "90" Identifi)
        (command "INSERT" (STRCAT RUTA "BLOCKS\\TEXTOPER") (suma PunTex 0 -25) "3" "3" "90" Elev)
        (command "INSERT" (STRCAT RUTA "BLOCKS\\TEXTOPER") (suma PunTex 0 -55) "3" "3" "90" TEXTOPER)
        (command "INSERT" (STRCAT RUTA "BLOCKS\\TEXTOPER") (suma PunTex 0 -85) "3" "3" "90" texto1)
        (setq PunPer2 (list disac (* (atof elev) exagera)))
        (command "LINE" (suma PunTex 0 12) PunPer2 "")
        (command "CHANGE" (entlast) "" "P" "C" "1" "")
      )
    )
    (if (/= vez 0)
      (progn
        (setq dis (distance PunVerA PunVer))
        (setq disac (+ disac dis))
        (setq PunPer1 (list disA (* (atof elevA) exagera)))
        (setq PunPer2 (list disac (* (atof elev) exagera)))
        (command "LINE" PunPer1 PunPer2 "")
        (setq PunTex (list disac (- elevmin 15)))
        (setq texto1 (cottop (atof (rtos disac 2 3))))
        (setq TEXTOPER (rtos dis 2 3))
        (command "INSERT" (STRCAT RUTA "BLOCKS\\TEXTOPER") PunTex "3" "3" "90" Identifi)
        (command "INSERT" (STRCAT RUTA "BLOCKS\\TEXTOPER") (suma PunTex 0 -25) "3" "3" "90" Elev)
        (command "INSERT" (STRCAT RUTA "BLOCKS\\TEXTOPER") (suma PunTex 0 -55) "3" "3" "90" TEXTOPER)
        (command "INSERT" (STRCAT RUTA "BLOCKS\\TEXTOPER") (suma PunTex 0 -85) "3" "3" "90" texto1)
        (command "LINE" (suma PunTex 0 12) PunPer2 "")
        (command "CHANGE" (entlast) "" "P" "C" "1" "")
      )
    )
    (setq cuenta (+ cuenta 1))
    (setq vez 1)
  )
  (command "LAYER" "S" "RETICULA" "")
  (command "LINE" (strcat "-3," (rtos elevmin)) (strcat (rtos disac) "," (rtos elevmin)) "")
  (command "CHANGE" (entlast) "" "P" "C" "3" "")
  (command "INSERT" (STRCAT RUTA "BLOCKS\\TEXTOPER") (suma (cdr (assoc 10 (entget (entlast))))  -25 0) "3" "3" "0" (rtos (/ elevmin EXAGERA) 2 2))
  (setq NoLin (/ (- (/ elevmax exagera) (/ elevmin exagera)) sepret))
  (setq cucu sepret)
  (setq CNoLin 1)
  (while (/= CNoLin NoLin)
    (setq cucu2 (* cucu exagera))
    (command "LINE" (strcat "-3," (rtos (+ elevmin cucu2))) (strcat (rtos disac) "," (rtos (+ elevmin cucu2))) "")
    (command "CHANGE" (entlast) "" "P" "LT" "HIDDEN" "")
    (command "INSERT" (STRCAT RUTA "BLOCKS\\TEXTOPER") (suma (cdr (assoc 10 (entget (entlast))))  -25 0) "3" "3" "0" (rtos (+ (/ elevmin exagera) cucu) 2 2))
    (setq cucu (+ cucu sepret))
    (setq CNoLin (+ CNoLin 1))
  )
  (setq cucu2 (* cucu exagera))
  (command "LINE" (strcat "-3," (rtos (+ elevmin cucu2))) (strcat (rtos disac) "," (rtos (+ elevmin cucu2))) "")
  (command "CHANGE" (entlast) "" "P" "LT" "HIDDEN" "")
  (command "CHANGE" (entlast) "" "P" "C" "3" "")
  (command "CHANGE" (entlast) "" "P" "LT" "CONTINUOUS" "")
  (command "INSERT" (STRCAT RUTA "BLOCKS\\TEXTOPER") (suma (cdr (assoc 10 (entget (entlast))))  -25 0) "3" "3" "0" (rtos (+ (/ elevmin exagera) cucu) 2 2))
  (command "LINE" (strcat "0," (rtos elevmin)) (strcat "0," (rtos (+ elevmin cucu2))) "")
  (command "CHANGE" (entlast) "" "P" "C" "3" "")
  (command "LINE" (strcat (rtos disac) "," (rtos elevmin)) (strcat (rtos disac) "," (rtos (+ elevmin cucu2))) "")
  (command "CHANGE" (entlast) "" "P" "C" "3" "")

;  (command "INSERT" (STRCAT RUTA "BLOCKS\\TEXTOPER") (strcat "-60," (rtos (- elevmin 14))) "4" "4" "0" "No. de Punto")
;  (command "LINE" (suma (cdr (assoc 10 (entget (entlast)))) 0 -3)  (strcat "@" (rtos (+ disac 60)) "<0") "")
;  (command "INSERT" "TEXTOPER" (strcat "-60," (rtos (- elevmin 32))) "4" "4" "0" "Cota del Terreno")
;  (command "LINE" (suma (cdr (assoc 10 (entget (entlast)))) 0 -10)  (strcat "@" (rtos (+ disac 60)) "<0") "")
;  (command "INSERT" "TEXTOPER" (strcat "-60," (rtos (- elevmin 60))) "4" "4" "0" "Distancia")
;  (command "LINE" (suma (cdr (assoc 10 (entget (entlast)))) 0 -13)  (strcat "@" (rtos (+ disac 60)) "<0") "")
;  (command "INSERT" "TEXTOPER" (strcat "-60," (rtos (- elevmin 90))) "4" "4" "0" "Cadenamiento")
;  (command "LINE" (suma (cdr (assoc 10 (entget (entlast)))) 0 -13)  (strcat "@" (rtos (+ disac 60)) "<0") "")


  (COMMAND "VIEW" "R" "HOLA")
)
