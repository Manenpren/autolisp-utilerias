(defun c:igual ()
  (setq e (car (entsel "Selecciona el OBJETO fuente: ")))
  (while (/= "INSERT" (cdr (assoc 0 (entget E))))
    (if (/= "INSERT" (cdr (assoc 0 (entget E))))
      (progn   
        (ALERT "\nEl objeto debe ser un block ")
        (setq E (car (entsel "\n Selecciona el bloque: ")))
      )
    )
  )
  (setq NOMBRE (cdr (assoc 2 (entget e))))
  (setq fs (cdr (assoc 41 (entget e))))
  (setq e2 (car (entsel "Selecciona el OBJETO destino: ")))
  (while (/= "INSERT" (cdr (assoc 0 (entget E2))))
    (if (/= "INSERT" (cdr (assoc 0 (entget E2))))
      (progn   
        (ALERT "\nEl objeto debe ser un block ")
        (setq E2 (car (entsel "\n Selecciona el bloque: ")))
      )
    )
  )
  (setq NOMBRE2 (cdr (assoc 2 (entget e2))))
  (setq fs2 (cdr (assoc 41 (entget e2))))
  (setq FSN (/ FS FS2))
  (setq E (entnext))
  (while E
  (setq XYZ (cdr (assoc 10 (entget E))))
   (if (= "INSERT" (cdr (assoc 0 (entget E))))
        (if (= (strcase NOMBRE) (cdr (assoc 2 (entget E))))
              (if (= FS2 (cdr (assoc 41 (entget E))))
                  (command "SCALE" (cdr (assoc -1 (entget E))) "" XYZ FSN)
              )
        )
   )
  (setq E (entnext E))
  )
)
