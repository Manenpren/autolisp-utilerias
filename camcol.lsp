(defun C:CAMCOL()
  (COMMAND "UNDO" "M")
  (COMMAND "VIEW" "S" "CAMCOL")
  (setq PROV (CAR (ENTSEL "SELECCIONA BLOCK")))
  (setq NOMBLO (cdr (assoc 2 (entget PROV))))
  (COMMAND "INSERT" NOMBLO "0,0" "" "" "")
  (SETQ X (ENTLAST))
  (COMMAND "EXPLODE" X "")
  (SETQ GPOA (SSGET "P"))
  (SETQ P 0)
  (WHILE (/= (cdr (assoc 0 (entget PROV))) "TEXT")
    (SETQ PROV (SSNAME GPOA P))
    (SETQ P (1+ P))
  )
  (setq XY (cdr (assoc 10 (entget PROV))))
;  (COMMAND "ZOOM" "C" XY "5")
;  (SETQ CADENA (CAR (ENTSEL "SELECCIONA EL CADENAMIENTO")))
;  (SETQ ELEVENT (CAR (ENTSEL "SELECCIONA LA ELEVACION")))
  (COMMAND "ZOOM" "C" XY "40")
;  (SETQ TN (CAR (ENTSEL "SELECCIONA LINEA DE TERRENO NATURAL")))
;  (COMMAND "CHANGE" CADENA "" "P" "C" "BLUE" "")
;  (COMMAND "CHANGE" ELEVENT "" "P" "C" "YELLOW" "")  
;  (COMMAND "PEDIT" TN "" "J" "ALL" "" "")
;  (SSADD (ENTLAST) GPOA)
;  (SETQ X (ENTLAST))
;  (COMMAND "CHANGE" X "" "P" "C" "GREEN" "")
;   (COMMAND "SCALE" CADENA "" (setq XYZ (cdr (assoc 10 (entget CADENA)))) "2")
;   (COMMAND "SCALE" ELEVENT "" (setq XYZ (cdr (assoc 10 (entget ELEVENT)))) "2")
   (setq linea (car (entsel "Selecciona la linea donde comenzar: ")))
   (setq linea2 (car (entsel "Selecciona la 2DA linea donde comenzar: ")))
   (SETQ PUN (cdr (assoc 10 (entget LINEA2))))
   (SETQ PUN2 (cdr (assoc 11 (entget LINEA2))))
;   (setq pun (getpoint "PUNTO DE INICIO : "))
;   (setq pun2 (getpoint "FIN : "))
;   (setq a (angle pun pun2))
;   (setq a (* 180 (/ a pi)))
:   (command "snap" "ro" pun a)
:   (command "snap" "off")
   (setq ds (distance pun pun2))
   (setq f (* ds 2))
   (setq f (FIX F))
   (command "array" linea "" "R" "" "2" "1")
   (SETQ GPOA (SSADD (ENTLAST) GPOA))
   (REPEAT (/ (- F 1) 2)
    (command "array" "LAST" "" "R" "" "2" "1")
    (SETQ GPOA (SSADD (ENTLAST) GPOA))
   )
;   (COMMAND "SNAP" "RO" "0,0" "0" "")
;   (setq f 60)
;   (command "array" linea2 "" "R" "" "2" "1")
;   (SETQ GPOA (SSADD (ENTLAST) GPOA))
;   (REPEAT (- F 1)
;    (command "array" "LAST" "" "R" "" "2" "1")
;    (SETQ GPOA (SSADD (ENTLAST) GPOA))
;   )
   (command "snap" "off")
   (COMMAND "BLOCK" NOMBLO "Y" "0,0" GPOA "")
   (COMMAND "VIEW" "R" "CAMCOL")
)
