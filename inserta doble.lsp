(defun c:is ()
    (COMMAND "UNDO" "M")
    (COMMAND "VIEW" "S" "C")
    (SETQ OPCIONESOS (GETVAR "OSMODE"))
    (SETVAR "OSMODE" 16384)
  (C:LIBRERIA "busca block en base de datos")
  (C:LIBRERIA "ZOOM ULTIMO OBJETO INSERTADO")
  (COMMAND "LUNITS" 2)
  (COMMAND "LUPREC" 7)
  (COMMAND "AUNITS" 0)
  (COMMAND "AUPREC" 4)
  (COMMAND "ANGDIR" 0)
  (COMMAND "ANGBASE" 0.0)
  (COMMAND "DIMZIN" 0)
    (setq texto (car (entsel "Selecciona el texto de cadenamiento: ")))
    (setq NOMBRE (cdr (assoc 1 (entget TEXTO))))
    (setq nomblo (strcat (substr NOMBRE 1 1) "-" (substr NOMBRE 3 4)))
    (setq elev (car (entsel "Selecciona el texto de elevacion : ")))
    (setq n2 (cdr (assoc 1 (entget elev))))
    (setq XYZT (cdr (assoc 10 (entget elev))))
    (setq elev2 (car (entsel "Selecciona el texto de elevacion2 : ")))
    (setq n22 (cdr (assoc 1 (entget elev2))))
    (setq XYZT2 (cdr (assoc 10 (entget elev2))))
    (setq xy (strcat "-4, " n2))
    (setq xy2 (strcat "4, " n22))
    (command "insert" nomblo "0,0" "" "" "")
  (SETQ X (ENTLAST))
  (ZBLOCK)
;    (COMMAND "EXPLODE" (ENTLAST) "")
    (command "insert" "ci" xy "" "" "")
    (COMMAND "EXPLODE" (ENTLAST) "")
    (command "insert" "cd" xy2 "" "" "")
    (COMMAND "EXPLODE" (ENTLAST) "")

    (command "CHANGE" texto elev elev2 "" "P" "C" "RED" "")
;    (COMMAND "COPY" TEXTO "" XYZT X1)
;    (COMMAND "ZOOM" "C" XY "20")
;    (COMMAND "CHANGE" (ENTLAST) "" "" "" "" "" "" N2)
;    (SETQ ARE (ATOF N2))
    (SETVAR "OSMODE" OPCIONESOS)

)
