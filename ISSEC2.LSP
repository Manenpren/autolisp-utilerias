(defun C:ISS ()
  (COMMAND "UNDO" "M")
  (COMMAND "VIEW" "S" "C")
  (setq PROV (CAR (ENTSEL "SELECCIONA BLOCK")))
  (setq NOMBLO (cdr (assoc 2 (entget PROV))))
  (COMMAND "INSERT" NOMBLO "0,0" "" "" "")
  (SETQ X (ENTLAST))
  (COMMAND "EXPLODE" X "")
  (SETQ GPOA (SSGET "P"))
  (SETQ P 0)
  (WHILE (/= (cdr (assoc 0 (entget PROV))) "TEXT")
    (SETQ PROV (SSNAME GPOA P))
    (SETQ P (1+ P))
  )
  (setq XY (cdr (assoc 10 (entget PROV))))
  (COMMAND "ZOOM" "C" XY "25")
  (C:1)
  (EXIT)
  (SETQ PROYG (SSGET))
  (COMMAND "ERASE" PROYG "")
  (COMMAND "BLOCK" NOMBLO "Y" "0,0" GPOA "")
  (COMMAND "VIEW" "R" "C")
  (C:2)
)

(DEFUN C:FIN ()
    (C:DY)
    (C:2)
    (setq T1 (CAR (ENTSEL "SELECCIONA TEXTO IGUAL")))
    (setq T2 (CAR (ENTSEL "SELECCIONA TEXTO IGUAL")))
    (COMMAND "SCALE" TEXTO "" (cdr (assoc 10 (entget TEXTO))) 2)
    (COMMAND "SCALE" T1 "" (cdr (assoc 10 (entget T1))) 0.8)
    (COMMAND "SCALE" T2 "" (cdr (assoc 10 (entget T2))) 0.8)
    (COMMAND "CHANGE" T1 "" "P" "LA" "TN" "")
    (COMMAND "CHANGE" T2 "" "P" "LA" "0" "")
    (C:MB)
    (COMMAND "VIEW" "R" "C")
)
