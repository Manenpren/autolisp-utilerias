(DEFUN C:EXRAN ()
  (command "undo" "m")
  (COMMAND "VIEW" "S" "PROV")
  (C:LIBRERIA "VERTICES DE UNA LWPOLYLINE")
  (C:LIBRERIA "BUSCA VALOR DE ATRIBUTO")
  (C:LIBRERIA "nombre carta topografica")
  (C:LIBRERIA "UTM-GEO")
  (C:LIBRERIA "CENTROIDE DE UN POLIGONO IRREGULAR2")
  (C:LIBRERIA "BUSCA CLAVE DE LOCALIDAD")
  (C:LIBRERIA "BUSCA CLAVE DE MUNICIPIO")
  (C:LIBRERIA "BUSCA CLAVE DEL EJIDO")
  (SETQ OPCIONESOS (GETVAR "OSMODE"))
  (command "osnap" "none")
  (IF (= NOMMUN NIL) (SETQ NOMMUN "X"))
  (SETQ NOMMUN1 (STRCASE (GETSTRING PROMPT (STRCAT "\n NOMBRE DEL MUNICIPIO <" NOMMUN ">:"))))
  (IF (/= NOMMUN1 "")
    (SETQ NOMMUN NOMMUN1)
  )
  (setq clmun (CLAVEMUNI NOMMUN))
  (IF (= (STRLEN CLMUN) 1) (SETQ CLMUN (STRCAT "00" CLMUN)))
  (IF (= (STRLEN CLMUN) 2) (SETQ CLMUN (STRCAT "0" CLMUN)))
  (IF (= CLMUN NIL) (SETQ CLMUN "XXX"))
  (SETQ CLMUN1 (GETSTRING (STRCAT "\n CLAVE DEL MUNICIPIO <" CLMUN ">:")))
  (IF (/= CLMUN1 "")
    (SETQ CLMUN CLMUN1)
  )
  (IF (= NOMEJI NIL) (SETQ NOMEJI "X"))
  (SETQ NOMEJI1 (STRCASE (GETSTRING PROMPT (STRCAT "\n NOMBRE DEL EJIDO <" NOMEJI ">:"))))
  (IF (/= NOMEJI1 "")
    (SETQ NOMEJI NOMEJI1)
  )
  (setq CLEJI (CLAVEJIDO nomEJI CLMUN))
  (IF (= (STRLEN CLEJI) 1) (SETQ CLEJI (STRCAT "00" CLEJI)))
  (IF (= (STRLEN CLEJI) 2) (SETQ CLEJI (STRCAT "0" CLEJI)))
  (IF (= CLEJI NIL) (SETQ CLEJI "XXX"))
  (SETQ CLEJI1 (GETSTRING (STRCAT "\n CLAVE DEL EJIDO <" CLEJI ">:")))
  (IF (/= CLEJI1 "")
    (SETQ CLEJI CLEJI1)
  )
  (IF (= NOMLOC NIL) (SETQ NOMLOC "X"))
  (SETQ NOMLOC1 (STRCASE (GETSTRING PROMPT (STRCAT "\n NOMBRE DE LA LOCALIDAD <" NOMLOC ">:"))))
  (IF (/= NOMLOC1 "")
    (SETQ NOMLOC NOMLOC1)
  )
  (setq clLOC (CLAVELOCALIDAD nomLOC CLMUN))
  (IF (= (STRLEN CLLOC) 1) (SETQ CLLOC (STRCAT "000" CLLOC)))
  (IF (= (STRLEN CLLOC) 2) (SETQ CLLOC (STRCAT "00" CLLOC)))
  (IF (= (STRLEN CLLOC) 3) (SETQ CLLOC (STRCAT "0" CLLOC)))
  (IF (= CLLOC NIL) (SETQ CLLOC "XXXX"))
  (SETQ CLLOC1 (GETSTRING (STRCAT "\n CLAVE DE LA LOCALIDAD <" CLLOC ">:")))
  (IF (/= CLLOC1 "")
    (SETQ CLLOC CLLOC1)
  )
  (if (= zonah nil) (setq zonah "00"))
  (SETQ zonah1 (GETSTRING (strcat "\n ZONA UTM HORARIA <" zonah ">:")))
  (IF (/= zonah1 "")
    (SETQ zonah zonah1)
  )
  (if (= zonae nil) (setq zonae "1"))
  (SETQ zonae1 (GETSTRING (strcat "\n ZONA DEL AREA EN CUESTION <" zonaE ">:")))
  (IF (/= zonaE1 "")
    (SETQ zonaE zonaE1)
  )
  (if (= npejid nil) (setq npejid "1"))
  (SETQ npejid2 (GETSTRING (strcat "\n NUMERO DE POLIGONO EJIDAL <" npejid ">:")))
  (IF (/= npejid2 "")
    (SETQ npejid npejid2)
  )
  (if (= ntpejid nil) (setq ntpejid "1"))
  (SETQ ntpejid2 (GETSTRING (strcat "\n NUMERO TOTAL DE POLIGONOS EJIDALES <" nTpejid ">:")))
  (IF (/= nTpejid2 "")
    (SETQ nTpejid nTpejid2)
  )
;  (SETQ TPREDIO (GETSTRING "\n TIPO DE PREDIO :"))
  (PROMPT "SELECCIONA LOS POLIGONOS DEL EJIDO Y LA CLINICA ")
  (setq gpoCLINEJID (ssget))
  (SETQ EX1 (SSNAME gpoCLINEJID 0))
  (SETQ EX2 (SSNAME gpoCLINEJID 1))
  (COMMAND "AREA" "E" EX1)
  (SETQ SUPEX1 (RTOS (GETVAR "AREA") 2 3))
  (COMMAND "AREA" "E" EX2)
  (SETQ SUPEX2 (RTOS (GETVAR "AREA") 2 3))
  (IF (> (ATOF SUPEX1) (ATOF SUPEX2))
    (PROGN
      (SETQ ENTCLIN EX2)
      (SETQ SUPCLIN SUPEX2)
      (SETQ ENTEJI EX1)
      (SETQ SUPEJI SUPEX1)
    )
  )
  (IF (> (ATOF SUPEX2) (ATOF SUPEX1))
    (PROGN
      (SETQ ENTCLIN EX1)
      (SETQ SUPCLIN SUPEX1)
      (SETQ ENTEJI EX2)
      (SETQ SUPEJI SUPEX2)
    )
  )

  (setq xyz2 (ax:centroid entclin))
  (setq xyz (ax:centroid enteji))
  (PROMPT "SELECCIONA LAS LINEAS DE SEPARACION DE LINDERO")
  (setq gpoLINDL (ssget))
  (command "saveas" "dxf" "V" "2000" "o" "" (STRCAT "C:\\EXTRAE\\A" CLMUN "0" CLEJI ".DXF"))            ;ARCHIVO DE AFECTACIONES
  (setq ARCH (open (STRCAT "C:\\EXTRAE\\A" CLMUN "0" CLEJI ".TXT") "w"))
  (CLOSE ARCH)
  (setq NOMBRECARTA (CARTAING (UTM-GEO xyz (ATOI ZONAH))))
  (setq ARCH (open (STRCAT "C:\\EXTRAE\\C" CLMUN "0" CLEJI ".CE1") "w"))                 ;CEDULA DE INFORMACION DE VERTICES GEODESICOS
  (SETQ LINEA (STRCAT "16," (CHR 34) "MICHOACAN DE OCAMPO" (CHR 34) "," (itoa (ATOI CLMUN)) "," (CHR 34) NOMMUN (CHR 34) "," (itoa (ATOI CLEJI)) (CHR 34) NOMEJI (CHR 34) "," npejid "," (CHR 34) NOMBRECARTA (CHR 34) "," (CHR 34) "16000000" (CHR 34) "," (CHR 34) "181105" (CHR 34) ",19,58,39.5684,102,36,51.3224,749652.141,2210785.446," ZONAH "," (CHR 34) "0" (CHR 34) ",0,0"  "," (CHR 34) "0" (CHR 34) ",0,0" "," (CHR 34) "0" (CHR 34) ",0,0"))
  (write-line LINEA arcH)
  (CLOSE ARCH)
  (setq ARCH (open (STRCAT "C:\\EXTRAE\\C" CLMUN "0" CLEJI ".CE2") "w"))                 ;CEDULA DE INFORMACION AL INTERIOR DEL EJIDO
  (SETQ LINEA (STRCAT "16," (CHR 34) "MICHOACAN DE OCAMPO" (CHR 34) "," (itoa (ATOI CLMUN)) "," (CHR 34) NOMMUN (CHR 34) "," (itoa (ATOI CLEJI)) "," (CHR 34) NOMEJI (CHR 34) "," ntpejid "," npejid "," (CHR 34) "A" (CHR 34) "," (CHR 34) NOMBRECARTA (CHR 34) ",0,0,0,1,1,0," "16," "MICHOACAN DE OCAMPO" "," (itoa (ATOI CLMUN)) "," NOMMUN ",0,0,0," SUPEJI ",0,0,0,0.000,0.000,0.000"))
  (write-line LINEA arcH)
  (CLOSE ARCH)
  (setq ARCH (open (STRCAT "C:\\EXTRAE\\C" CLMUN "0" CLEJI ".CE5") "w"))                 ;CEDULA DE INFORMACION PARCELARIA
;  (SETQ LINEA (STRCAT "16," CLMUN "," CLEJI ",01,06," zonah ",00000,nombre ejidatario,fechanac," supclin ",0.000,0.000,0.000,0.000,0.000,16," (CHR 34) "MICHOACAN DE OCAMPO" (CHR 34) "," CLMUN "," NOMMUN))
;  (write-line LINEA arcH)
  (CLOSE ARCH)
  (setq ARCH (open (STRCAT "C:\\EXTRAE\\C" CLMUN "0" CLEJI ".CE7") "w"))                 ;CEDULA DE INFORMACION DE SOLARES URBANOS
  (SETQ LINEA (STRCAT "16," (itoa (ATOI CLMUN)) "," (itoa (ATOI CLEJI)) "," npejid "," (CHR 34) "J" (CHR 34) "," (CHR 34) "2" (CHR 34) "," (itoa (ATOI clloc)) "," (CHR 34) nomloc (CHR 34) ",1,1," (CHR 34) "CLINICA IMSS" (CHR 34) "," (CHR 34) (CHR 34) "," supclin ",0.000,0.000,0.000,0.000,0.000,0.000,0," (CHR 34) (CHR 34) ",0," (CHR 34) (CHR 34)))
  (write-line LINEA arcH)
  (CLOSE ARCH)
  (SETQ GPOCOL (SSADD))
  (SETQ VERTX (vertice ENTEJI 1))
  (SETQ CONT1 2)
  (WHILE VERTX
    (SETQ VERT2 VERTX)
    (SETQ VERTX (vertice ENTEJI CONT1))
    (SETQ CONT1 (1+ CONT1))
    (IF (/= VERTX NIL)
      (PROGN
        (setq pun1 VERTX) 
        (setq pun2 VERT2) 
        (setq x1 (car pun1))
        (setq y1 (car (cdr pun1)))
        (setq x2 (car pun2))
        (setq y2 (car (cdr pun2)))
        (setq xd (- x1 x2))
        (if (> 0 xd)
          (setq xd (* xd -1))
        )
        (setq xd (/ xd 2))
        (setq yd (- y1 y2))
        (if (> 0 yd)
          (setq yd (* yd -1))
        )
        (setq yd (/ yd 2))
        (if (> x1 x2)
          (setq xd (+ xd x2))
          (setq xd (+ xd x1))
        )
        (if (> y1 y2)
          (setq yd (+ yd y2))
          (setq yd (+ yd y1))
        )
        (setq punmid (list xd yd 0))  
        (SETQ CONTX (- CONT1 2))
        (SETQ XYZX (CONS 10 PUNMID))
        (SETQ TEXTX (CONS 1 (ITOA CONTX)))
        (ENTMAKE (LIST '(0 . "TEXT") '(100 . "AcDbEntity") '(8 . "0") '(100 . "AcDbText") XYZX '(40 . 1) TEXTX))
        (SSADD (ENTLAST) GPOCOL)
      )
    )
  );WHILE
  (SETQ GPOCOL2 (SSADD))
  (SETQ EX (SSNAME GPOLINDL 0))
  (SETQ CONT1 1)
  (WHILE EX
    (SETQ PUN1 (vertice EX 1))
    (SETQ PUN2 (vertice EX 2))
    (setq x1 (car pun1))
    (setq y1 (car (cdr pun1)))
    (setq x2 (car pun2))
    (setq y2 (car (cdr pun2)))
    (setq xd (- x1 x2))
    (if (> 0 xd)
      (setq xd (* xd -1))
    )
    (setq xd (/ xd 2))
    (setq yd (- y1 y2))
    (if (> 0 yd)
      (setq yd (* yd -1))
    )
    (setq yd (/ yd 2))
    (if (> x1 x2)
      (setq xd (+ xd x2))
      (setq xd (+ xd x1))
    )
    (if (> y1 y2)
      (setq yd (+ yd y2))
      (setq yd (+ yd y1))
    )
    (setq punmid (list xd yd 0))  
    (SETQ XYZX (CONS 10 PUNMID))
    (SETQ TEXTX (CONS 1 (ITOA CONTX)))
    (ENTMAKE (LIST '(0 . "TEXT") '(100 . "AcDbEntity") '(8 . "0") '(100 . "AcDbText") XYZX '(40 . 1) '(1 . "0")))
    (SSADD (ENTLAST) GPOCOL2)
    (SETQ EX (SSNAME GPOLINDL CONT1))
    (SETQ CONT1 (1+ CONT1))
  )
  (command "saveas" "dxf" "v" "2000" "o" GPOCOL GPOCOL2 gpoLINDL ENTEJI "" "" (STRCAT "C:\\EXTRAE\\C" CLMUN "0" CLEJI ".DXF"))      ;ARCHIVOS DE COLINDANCIAS
  (setq ARCH (open (STRCAT "C:\\EXTRAE\\C" CLMUN "0" CLEJI ".TXT") "w"))
  (REPEAT (sslength GPOCOL2)
    (SETQ LINEA (STRCAT "0,"(CHR 34) (CHR 34)))
    (write-line LINEA arcH)
  )
  (CLOSE ARCH)
  (COMMAND "SHELL" (STRCAT "COPY D:\\FORMAT~1\\L1040011.DXF C:\\EXTRAE\\L" CLMUN "0" CLEJI ".DXF"))
  (setq ARCH (open (STRCAT "C:\\EXTRAE\\M" CLMUN "0" CLEJI ".TXT") "w"))
  (SETQ LINEA (STRCAT "Ing. Mario Fernández Arreygue"))
  (write-line LINEA arcH)
  (SETQ LINEA (STRCAT ""))
  (write-line LINEA arcH)
  (SETQ LINEA (STRCAT ""))
  (write-line LINEA arcH)
  (SETQ LINEA (STRCAT ""))
  (write-line LINEA arcH)
  (SETQ LINEA (STRCAT ""))
  (write-line LINEA arcH)
  (SETQ LINEA (STRCAT ""))
  (write-line LINEA arcH)
  (SETQ LINEA (STRCAT ""))
  (write-line LINEA arcH)
  (CLOSE ARCH)
  (IF (< (atoi NPEJID) 9) (SETQ NPEJID2 (STRCAT "0" NPEJID)) (SETQ NPEJID2 NPEJID))
  (SETQ GPOX (SSADD))
  (SETQ XYZX (CONS 10 XYZ))
  (SETQ TEXTX (CONS 1 (STRCAT npejid2 CLLOC ZONAE "00100001001")))
  (ENTMAKE (LIST '(0 . "TEXT") '(100 . "AcDbEntity") '(8 . "0") '(100 . "AcDbText") XYZX '(40 . 10) TEXTX))
  (SSADD (ENTLAST) GPOX)
  (SETQ XYZX (CONS 10 XYZ2))
  (SETQ TEXTX (CONS 1 (STRCAT npejid2 CLLOC ZONAE "00100001002")))
  (ENTMAKE (LIST '(0 . "TEXT") '(100 . "AcDbEntity") '(8 . "0") '(100 . "AcDbText") XYZX '(40 . 10) TEXTX))
  (SSADD (ENTLAST) GPOX)
  (command "saveas" "dxf" "v" "2000" "o" ENTCLIN ENTEJI GPOX "" ""(STRCAT "C:\\EXTRAE\\P" CLMUN "0" CLEJI ".DXF"))     ;ARCHIVOS DE POLIGONOS
  (setq ARCH (open (STRCAT "C:\\EXTRAE\\P" CLMUN "0" CLEJI ".TXT") "w"))
  (SETQ TXT (STRCAT (CHR 34) npejid2 CLLOC ZONAe "00000000001" (CHR 34) ",09," (CHR 34) "RESERVA DE CRECIMIENTO" (CHR 34) "," (CHR 34) "T" (CHR 34) "," (CHR 34) (CHR 34) ",0"))
  (write-line TXT arcH)
  (SETQ TXT (STRCAT (CHR 34) npejid2 CLLOC ZONAe "00100000001" (CHR 34) ",06," (CHR 34) "CLINICA IMSS" (CHR 34) "," (CHR 34) "S" (CHR 34) "," (CHR 34) (CHR 34) ",0"))
  (write-line TXT arcH)
  (CLOSE ARCH)
  (SETQ GPOBLEJI (SSADD))
  (SETQ VERTX (vertice ENTEJI 1))
  (SETQ CONT1 2)
  (WHILE VERTX
    (setq punver1 (suma VERTX -0.01 -0.01))
    (setq punver2 (suma VERTX 0.01 0.01))
    (command "ZOOM" "W" punver1 punver2)
    (setq GpoPun (ssget "C" punver1 punver2 '((2 . "PUNTO"))))
    (IF (= 0 (SSLENGTH GPOPUN)) (PROGN (ALERT "FALTA BLOCK EN VERTICE") (COMMAND "ZOOM" "C" VERTX "10")))
    (COMMAND "ZOOM" "P")
    (SSADD (SSNAME GPOPUN 0) GPOBLEJI)
    (SETQ VERTX (vertice ENTEJI CONT1))
    (SETQ CONT1 (1+ CONT1))
  );WHILE
  (PROMPT "SELECCIONA LOS vertices de la clinica")
  (setq gpoblcli (ssget '((2 . "PUNTO"))))
  (SETQ GPOVERTX (SSADD))
  (SETQ EX (SSNAME GPOBLEJI 0))
  (SETQ CONT1 1)
  (setq ARCH (open (STRCAT "C:\\EXTRAE\\S" CLMUN "0" CLEJI ".TXT") "w"))
  (WHILE EX
    (setq XYZX (ASSOC 10 (ENTGET EX)))  
    (setq NPTO (busatr EX "PUNTO"))  
    (SETQ CADENAX (STRCAT (NTOS (ATOI NPTO)) "2900"))
    (SETQ TEXTX (CONS 1 CADENAX))
    (ENTMAKE (LIST '(0 . "TEXT") '(100 . "AcDbEntity") '(8 . "0") '(100 . "AcDbText") XYZX '(40 . 5) TEXTX))
    (SSADD (ENTLAST) GPOVERTX)
    (ENTMAKE (LIST '(0 . "POINT") '(8 . "0") XYZX))
    (SSADD (ENTLAST) GPOVERTX)
    (SETQ EX (SSNAME GPOBLEJI CONT1))
    (SETQ CONT1 (1+ CONT1))
    (SETQ LINEA (STRCAT CADENAX "," (CHR 34) (CHR 34)))
    (write-line LINEA arcH)
  )
  (SETQ EX (SSNAME GPOBLCLI 0))
  (SETQ CONT1 1)
  (WHILE EX
    (setq XYZX (ASSOC 10 (ENTGET EX)))  
    (setq NPTO (busatr EX "PUNTO"))  
    (SETQ CADENAX (STRCAT (NTOS (ATOI NPTO)) "3900"))
    (SETQ TEXTX (CONS 1 CADENAX))
    (ENTMAKE (LIST '(0 . "TEXT") '(100 . "AcDbEntity") '(8 . "0") '(100 . "AcDbText") XYZX '(40 . 5) TEXTX))
    (SSADD (ENTLAST) GPOVERTX)
    (ENTMAKE (LIST '(0 . "POINT") '(8 . "0") XYZX))
    (SSADD (ENTLAST) GPOVERTX)
    (SETQ EX (SSNAME GPOBLCLI CONT1))
    (SETQ CONT1 (1+ CONT1))
    (SETQ LINEA (STRCAT CADENAX "," (CHR 34) "clinica del imss" (CHR 34)))
    (write-line LINEA arcH)
  )
  (CLOSE ARCH)
  (command "saveas" "dxf" "v" "2000" "o" GPOVERTX "" "" (STRCAT "C:\\EXTRAE\\S" CLMUN "0" CLEJI ".DXF"))
)

(DEFUN NTOS (NUM)
  (SETQ F (STRLEN (ITOA NUM)))
  (SETQ FS (ITOA NUM))
  (REPEAT (- 5 F)
    (SETQ FS (STRCAT "0" FS))
  )
  (SETQ NUM FS)
)

(DEFUN C:PPRAN()
  (command "undo" "m")
  (COMMAND "VIEW" "S" "PROV")
  (C:LIBRERIA "BUSCA VALOR DE ATRIBUTO")
  (C:LIBRERIA "BUSCA CLAVE DE LOCALIDAD")
  (C:LIBRERIA "BUSCA CLAVE DE MUNICIPIO")
  (C:LIBRERIA "sup metros cubicos a hectareas")
  (C:LIBRERIA "BUSCA CLAVE DEL EJIDO")
  (SETQ OPCIONESOS (GETVAR "OSMODE"))
  (command "osnap" "none")
  (SETQ ESCALA1 NIL)
  (SETQ NOMMUN1 NIL)
  (SETQ CLMUN1 NIL)
  (SETQ NOMEJI1 NIL)
  (SETQ CLEJI1 NIL)
  (DIALOGO)
;  (COMMAND "VIEW" "R" "PROV")
  (SETVAR "OSMODE" OPCIONESOS)
)

(DEFUN DIALOGO ()
; (setq res nil)
; (setq dcl_id (load_dialog (strcat ruta "dialogos\\PPRAN.dcl"))) 
; (if (not (new_dialog "pping" dcl_id))   
;   (exit)                                
;                                         
; )
; (setq width (dimx_tile  "arcsv")
;       height (dimy_tile "arcsv"))
; (start_image "arcsv")  
; (slide_image 1 1 width height (STRCAT RUTA "SLIDES\\PPINEGI.SLD"))
; (end_image)
; (start_image "poli")  
; (slide_image 1 1 width height (STRCAT RUTA "SLIDES\\PPINEGI2.SLD"))
; (end_image)

;  (action_tile "arcsv" "(v1)")
;  (action_tile "poli" "(v2)")
;  (start_dialog)                          
                                          
;  (if (= res "A")
;    (progn
;      (if (not (new_dialog "pping2" dcl_id))   
;        (exit)                                
;                                              
;      )
;      (action_tile "accept" "(leevar)")
;      (start_dialog)  
;      (if (= nomblo "0") (setq escala 1))
;      (if (= nomblo "1") (setq escala 2))
;      (if (= nomblo "2") (setq escala 2.5))
;      (if (= nomblo "3") (setq escala 5))
;      (if (= nomblo "4") (setq escala 10))
;      (if (= nomblo "5") (setq escala 20))
;      (if (= nomblo "6") (setq escala 25))
;      (if (= nomblo "7") (setq escala 50))
;      (if (= nomblo "8") (setq escala 100))
;      (if (= nomblo "9") (setq escala 200))
;      (if (= nomblo "10") (setq escala 400))
;      (if (= nomblo "11") (setq escala 500))
;      (ppgrande)
;    )
;  )
;  (if (= res "P")
;    (progn
;      (if (not (new_dialog "pping2" dcl_id))   
;        (exit)                                
;                                              
;      )
;      (action_tile "accept" "(leevar)")
;      (start_dialog)  
;      (if (= nomblo "0") (setq escala 1))
;      (if (= nomblo "1") (setq escala 2))
;      (if (= nomblo "2") (setq escala 2.5))
;      (if (= nomblo "3") (setq escala 5))
;      (if (= nomblo "4") (setq escala 10))
;      (if (= nomblo "5") (setq escala 20))
;      (if (= nomblo "6") (setq escala 25))
;      (if (= nomblo "7") (setq escala 50))
;      (if (= nomblo "8") (setq escala 100))
;      (if (= nomblo "9") (setq escala 200))
;      (if (= nomblo "10") (setq escala 400))
;      (if (= nomblo "11") (setq escala 500))
;      (ppchico)
;    )
;  )
;  (unload_dialog dcl_id)                  
;  (princ)
  (C:LIBRERIA "VERTICES DE UNA LWPOLYLINE")
  (C:LIBRERIA "SEPARA VALORES DE COMAS DE UN TEXTO TO LISTA")
  (SETQ TIPOPLANO (GETSTRING "\n TIPO DE PLANO? ('A'sentamientos/'U'so comun/'I'nterno/'P'arcela/'S'olar):"))
  (if (= (strcase tipoplano) "S")
    (progn
     (setq lescalas "100,200,500,1000,1500")                                            ;ESCALAS NORMATIVA INEGI
     (SETQ lescalas2 (SEPARA_VAL_COMAS lescalas))
    )
  )
  (if (= (strcase tipoplano) "P")
    (progn
     (setq lescalas "200,500,1000,2500,5000,10000,20000,50000,75000,100000")
     (SETQ lescalas2 (SEPARA_VAL_COMAS lescalas))
    )
  )
  (if (= (strcase tipoplano) "I")
    (progn
     (setq lescalas "1000,2500,5000,10000,20000,40000,50000,100000,125000,150000,175000,200000")
     (SETQ lescalas2 (SEPARA_VAL_COMAS lescalas))
    )
  )
  (if (= (strcase tipoplano) "U")
    (progn
     (setq lescalas "500,1000,2500,5000,10000,20000,50000,100000,125000,150000,175000,200000")
     (SETQ lescalas2 (SEPARA_VAL_COMAS lescalas))
    )
  )
  (if (= (strcase tipoplano) "A")
    (progn
     (setq lescalas "500,1000,2500,5000")
     (SETQ lescalas2 (SEPARA_VAL_COMAS lescalas))
    )
  )
  (setq poli (car (entsel "\n Selecciona la poligonal envolvente: ")))
  (SETQ PROV 1)
  (SETQ P1T (VERTICE POLI PROV))
  (SETQ XMENOR (CAR P1T))
  (SETQ YMENOR (CADR P1T))
  (SETQ XMAYOR XMENOR)
  (SETQ YMAYOR YMENOR)
  (SETQ PROVV P1T)
  (while p1t
    (SETQ X2PROV (CAR P1T))
    (SETQ Y2PROV (CADR P1T))
    (IF (AND (< X2PROV XMENOR) (/= X2PROV nil)) (SETQ XMENOR X2PROV))
    (IF (AND (< Y2PROV YMENOR) (/= Y2PROV nil)) (SETQ YMENOR Y2PROV))
    (IF (AND (> X2PROV XMAYOR) (/= X2PROV nil)) (SETQ XMAYOR X2PROV))
    (IF (AND (> Y2PROV YMAYOR) (/= Y2PROV nil)) (SETQ YMAYOR Y2PROV))
    (SETQ PROV (1+ PROV))
    (SETQ P1T (VERTICE POLI PROV))
  )

  (setq dosx (* (- xmayor xmenor) 0.30))
  (setq dosy (* (- ymayor ymenor) 0.30))
  (COMMAND "ZOOM" "W" (STRCAT (RTOS (- XMENOR dosx) 2 6) "," (RTOS (- YMENOR dosy) 2 6)) (STRCAT (RTOS (+ XMAYOR dosx) 2 6) "," (RTOS (+ YMAYOR dosy) 2 6)))
  (REDRAW POLI 3)
  (IF (OR (= (strcase tipoplano) "A") (= (strcase tipoplano) "U") (= (strcase tipoplano) "I"))
    (PROGN
      (SETQ DIMX 0.84)
      (SETQ DIMY 0.78)
    )
    (PROGN
      (SETQ DIMX 0.193)
      (SETQ DIMY 0.166)
    )
  )
  (if (< (/ (- ymayor ymenor) (- xmayor xmenor)) 0.92857)
    (PROGN
      (setq dsten (+ (- xmayor xmenor) (/ dosx 20)))
      (setq escalal (ATOI (cdr (assoc 1 lescalas2))))
      (setq cont 2)
      (SETQ COMPROB2 10)
      (SETQ ESCALA NIL)
      (while escalal
        (setq comprob (/ (* DIMX escalal) dsten))
        (if (AND (< comprob COMPROB2) (> comprob 1))
          (progn 
            (SETQ ESCALA ESCALAL)
            (setq escalal (cdr (assoc cont lescalas2)))
            (IF (/= ESCALAL NIL) (SETQ ESCALAL (ATOI ESCALAL)))
            (SETQ COMPROB2 COMPROB)
            (setq conth cont)
            (setq cont (1+ cont))
          )
          (progn 
            (setq escalal (cdr (assoc cont lescalas2)))
            (IF (/= ESCALAL NIL) (SETQ ESCALAL (ATOI ESCALAL)))
            (setq cont (1+ cont))
          )
        )
      )
    )
    (PROGN
      (setq dsten (+ (- ymayor ymenor) (/ dosy 20)))
      (setq escalal (ATOI (cdr (assoc 1 lescalas2))))
      (setq cont 2)
      (SETQ COMPROB2 10)
      (SETQ ESCALA NIL)
      (while escalal
        (setq comprob (/ (* DIMY escalal) dsten))
        (if (AND (< comprob COMPROB2) (> comprob 1))
          (progn
            (SETQ ESCALA ESCALAL)
            (SETQ CONTH CONT)
            (setq escalal (cdr (assoc cont lescalas2)))
            (IF (/= ESCALAL NIL) (SETQ ESCALAL (ATOI ESCALAL)))
            (SETQ COMPROB2 COMPROB)
            (setq cont (1+ cont))
          )
          (progn 
            (setq escalal (cdr (assoc cont lescalas2)))
            (IF (/= ESCALAL NIL) (SETQ ESCALAL (ATOI ESCALAL)))
            (setq cont (1+ cont))
          )
        )
      )
    )
  )
  (SETQ ESCALA (/ ESCALA 100))
  (setq escatras (cdr (assoc (- contH 2) lescalas2)))
  (setq escadel (cdr (assoc contH lescalas2)))
  (if (= escatras nil) (setq escatras "n/a"))
  (if (= escadel nil) (setq escadel "n/a"))
  (setq escalal (getint (strcat "Escala plano //" escatras "//  <1:" (itoa (* escala 100)) ">  //" escadel "// :")))
  (if escalal
    (setq escala (/ escalal 100))
  )
  (IF (OR (= (strcase tipoplano) "A") (= (strcase tipoplano) "U") (= (strcase tipoplano) "I"))
    (PROGN
      (PPGRANDE)
      (COMMAND "ZOOM" "W" (STRCAT (RTOS (- Xv (* ESCALA 105)) 2 6) "," (RTOS yv 2 6)) (STRCAT (RTOS (+ Xv (* ESCALA 1)) 2 6) "," (RTOS (+ yv (* ESCALA 86)) 2 6)))
    )
    (PROGN
      (PPCHICO)
;      (COMMAND "ZOOM" "W" (STRCAT (RTOS (- Xv (* ESCALA 21.2739)) 2 6) "," (RTOS (- yv (* ESCALA 2.1983)) 2 6)) (STRCAT (RTOS (+ Xv (* ESCALA 14.2938)) 2 6) "," (RTOS (+ yv (* ESCALA 19.4017)) 2 6)))
    )
  )
)

(defun v1 ()
  (setq res "A")
  (done_dialog)
)

(defun v2 ()
  (setq res "P")
  (done_dialog)
)

(defun leevar ()
  (setq nomblo (get_tile "Nblock"))
  (done_dialog)
)

(defun ppgrande ()
  (C:LIBRERIA "VERTICES DE UNA LWPOLYLINE")
  (C:LIBRERIA "CENTROIDE DE UN POLIGONO IRREGULAR2")
  (setq punver1 (list xmenor ymenor))
  (setq punver2 (list xmayor ymayor))
  (setq escgpo (ssget "C" punver1 punver2 '((0 . "INSERT"))))
  (setq ej (ssname escgpo 0))
  (setq t1 1)
  (while Ej
    (setq fs2 (cdr (assoc 41 (entget ej))))
    (setq FSN (/ (* escala 0.2) FS2))
    (setq XYZ (cdr (assoc 10 (entget Ej))))
      (if (= "PUNTO" (cdr (assoc 2 (entget Ej))))
        (command "SCALE" (cdr (assoc -1 (entget Ej))) "" XYZ fsn)
      )
      (setq Ej (ssname escgpo t1))
      (setq t1 (1+ t1))
  )
  (setq opcion (strcase TIPOPLANO))
  (SETQ CENTROIDEY1 (+ (/ (- YMAYOR YMENOR) 2) YMENOR))
  (SETQ CENTROIDEX1 (+ (/ (- XMAYOR XMENOR) 2) XMENOR))
  (SETQ Y (- CENTROIDEY1 (* ESCALA 43)))
  (SETQ X (+ CENTROIDEX1 (* ESCALA 58)))
  (if (= (strcase TIPOPLANO) "A") (setq nblock "pPINEGI-2.dwg"))
  (if (= (strcase TIPOPLANO) "I") (setq nblock "pPINEGI.dwg"))
  (if (= (strcase TIPOPLANO) "U") (setq nblock "PPINEGI-3.DWG"))
  (if (= (getvar "acadver") "17.1s (LMS Tech)")
    (COMMAND "INSERt" (STRCAT RUTA "BLOCKS\\" nblock) "s" ESCALA (strcat (rtos x 2 6) "," (rtos y 2 6)) "")
    (COMMAND "INSERt" (STRCAT RUTA "BLOCKS\\" nblock) ESCALA (strcat (rtos x 2 6) "," (rtos y 2 6)) ESCALA "" "")
  )
  (setq PTO (cons 10 (list x y 0))) 
  (COMMAND "EXPLODE" (ENTLAST) "")
  (IF (= NOMMUN NIL) (SETQ NOMMUN "X"))
  (SETQ NOMMUN1 (STRCASE (GETSTRING PROMPT (STRCAT "\n NOMBRE DEL MUNICIPIO <" NOMMUN ">:"))))
  (IF (/= NOMMUN1 "")
    (SETQ NOMMUN NOMMUN1)
  )
  (setq clmun (CLAVEMUNI nommun))
  (IF (= (STRLEN CLMUN) 1) (SETQ CLMUN (STRCAT "00" CLMUN)))
  (IF (= (STRLEN CLMUN) 2) (SETQ CLMUN (STRCAT "0" CLMUN)))
  (IF (= CLMUN NIL) (SETQ CLMUN "XXX"))
  (SETQ CLMUN1 (GETSTRING (STRCAT "\n CLAVE DEL MUNICIPIO <" CLMUN ">:")))
  (IF (/= CLMUN1 "")
    (SETQ CLMUN CLMUN1)
  )
  (IF (= NOMEJI NIL) (SETQ NOMEJI "X"))
  (SETQ NOMEJI1 (STRCASE (GETSTRING PROMPT (STRCAT "\n NOMBRE DEL EJIDO <" NOMEJI ">:"))))
  (IF (/= NOMEJI1 "")
    (SETQ NOMEJI NOMEJI1)
  )
  (setq CLEJI (CLAVEJIDO nomEJI CLMUN))
  (IF (= (STRLEN CLEJI) 1) (SETQ CLEJI (STRCAT "00" CLEJI)))
  (IF (= (STRLEN CLEJI) 2) (SETQ CLEJI (STRCAT "0" CLEJI)))
  (IF (= CLEJI NIL) (SETQ CLEJI "XXX"))
  (SETQ CLEJI1 (GETSTRING (STRCAT "\n CLAVE DEL EJIDO <" CLEJI ">:")))
  (IF (/= CLEJI1 "")
    (SETQ CLEJI CLEJI1)
  )
  (IF (= OPCION "A")   ;21.6865
    (PROGN
      (IF (= NOMLOC NIL) (SETQ NOMLOC "X"))
      (SETQ NOMLOC1 (STRCASE (GETSTRING PROMPT (STRCAT "\n NOMBRE DE LA LOCALIDAD <" NOMLOC ">:"))))
      (IF (/= NOMLOC1 "")
        (SETQ NOMLOC NOMLOC1)
      )
      (setq clLOC (CLAVELOCALIDAD nomLOC CLMUN))
      (IF (= (STRLEN CLLOC) 1) (SETQ CLLOC (STRCAT "000" CLLOC)))
      (IF (= (STRLEN CLLOC) 2) (SETQ CLLOC (STRCAT "00" CLLOC)))
      (IF (= (STRLEN CLLOC) 3) (SETQ CLLOC (STRCAT "0" CLLOC)))
      (IF (= CLLOC NIL) (SETQ CLLOC "XXXX"))
      (SETQ CLLOC1 (GETSTRING (STRCAT "\n CLAVE DE LA LOCALIDAD <" CLLOC ">:")))                  
      (IF (/= CLLOC1 "")
        (SETQ CLLOC CLLOC1)
      )
    )
  )
  (SETQ NIVEL (LIST (- X (* ESCALA 10.0674)) (+ Y (* ESCALA 68.7125)) 0))         ;0.279
  (SETQ XYZX (CONS 10 nivel))
  (SETQ XYZX2 (CONS 11 nivel))
  (setq tamanot (cons 40 (* ESCALA 0.25)))
  (setq layert (cons 8 "PP"))                            
  (SETQ TEXTX (CONS 1 NOMMUN))
  (ENTMAKE (LIST '(0 . "TEXT") '(100 . "AcDbEntity") layert '(100 . "AcDbText") XYZX tamanot TEXTX '(7 . "TIMES") '(72 . 0) xyzx2 '(73 . 0)))
  (SETQ NIVEL (LIST (- X (* ESCALA 3.16)) (+ Y (* ESCALA 68.7125)) 0))         ;0.279
  (SETQ XYZX (CONS 10 nivel))
  (SETQ XYZX2 (CONS 11 nivel))
  (SETQ TEXTX (CONS 1 CLMUN))
  (ENTMAKE (LIST '(0 . "TEXT") '(100 . "AcDbEntity") layert '(100 . "AcDbText") XYZX tamanot TEXTX '(7 . "TIMES") '(72 . 2) xyzx2 '(73 . 0)))
  (SETQ NIVEL (LIST (- X (* ESCALA 10.0674)) (+ Y (* ESCALA 68.1702)) 0))         ;0.279
  (SETQ XYZX (CONS 10 nivel))
  (SETQ XYZX2 (CONS 11 nivel))
  (SETQ TEXTX (CONS 1 NOMEJI))
  (ENTMAKE (LIST '(0 . "TEXT") '(100 . "AcDbEntity") layert '(100 . "AcDbText") XYZX tamanot TEXTX '(7 . "TIMES") '(72 . 0) xyzx2 '(73 . 0)))
  (SETQ NIVEL (LIST (- X (* ESCALA 3.16)) (+ Y (* ESCALA 68.1702)) 0))         ;0.279
  (SETQ XYZX (CONS 10 nivel))
  (SETQ XYZX2 (CONS 11 nivel))
  (SETQ TEXTX (CONS 1 CLEJI))
  (ENTMAKE (LIST '(0 . "TEXT") '(100 . "AcDbEntity") layert '(100 . "AcDbText") XYZX tamanot TEXTX '(7 . "TIMES") '(72 . 2) xyzx2 '(73 . 0)))
  (IF (= OPCION "A")
    (PROGN
      (SETQ NIVEL (LIST (- X (* ESCALA 10.0674)) (+ Y (* ESCALA 67.1327)) 0))         ;0.279
      (SETQ XYZX (CONS 10 nivel))
      (SETQ XYZX2 (CONS 11 nivel))
      (SETQ TEXTX (CONS 1 NOMLOC))
      (ENTMAKE (LIST '(0 . "TEXT") '(100 . "AcDbEntity") layert '(100 . "AcDbText") XYZX tamanot TEXTX '(7 . "TIMES") '(72 . 0) xyzx2 '(73 . 0)))
      (SETQ NIVEL (LIST (- X (* ESCALA 3.16)) (+ Y (* ESCALA 67.1327)) 0))         ;0.279
      (SETQ XYZX (CONS 10 nivel))
      (SETQ XYZX2 (CONS 11 nivel))
      (SETQ TEXTX (CONS 1 CLLOC))
      (ENTMAKE (LIST '(0 . "TEXT") '(100 . "AcDbEntity") layert '(100 . "AcDbText") XYZX tamanot TEXTX '(7 . "TIMES") '(72 . 2) xyzx2 '(73 . 0)))
      (SETQ NIVEL (LIST (- X (* ESCALA 10.0674)) (+ Y (* ESCALA 63.9180)) 0))         ;0.279
      (SETQ XYZX (CONS 10 nivel))
      (SETQ XYZX2 (CONS 11 nivel))
      (SETQ TEXTX (CONS 1 NOMMUN))
      (ENTMAKE (LIST '(0 . "TEXT") '(100 . "AcDbEntity") layert '(100 . "AcDbText") XYZX tamanot TEXTX '(7 . "TIMES") '(72 . 0) xyzx2 '(73 . 0)))
      (SETQ NIVEL (LIST (- X (* ESCALA 3.16)) (+ Y (* ESCALA 63.9180)) 0))         ;0.279
      (SETQ XYZX (CONS 10 nivel))
      (SETQ XYZX2 (CONS 11 nivel))
      (SETQ TEXTX (CONS 1 CLMUN))
      (ENTMAKE (LIST '(0 . "TEXT") '(100 . "AcDbEntity") layert '(100 . "AcDbText") XYZX tamanot TEXTX '(7 . "TIMES") '(72 . 2) xyzx2 '(73 . 0)))
    )
    (PROGN
      (SETQ NIVEL (LIST (- X (* ESCALA 10.0674)) (+ Y (* ESCALA 64.5796)) 0))         ;0.279
      (SETQ XYZX (CONS 10 nivel))
      (SETQ XYZX2 (CONS 11 nivel))
      (SETQ TEXTX (CONS 1 NOMMUN))
      (ENTMAKE (LIST '(0 . "TEXT") '(100 . "AcDbEntity") layert '(100 . "AcDbText") XYZX tamanot TEXTX '(7 . "TIMES") '(72 . 0) xyzx2 '(73 . 0)))
      (SETQ NIVEL (LIST (- X (* ESCALA 3.16)) (+ Y (* ESCALA 64.5796)) 0))         ;0.279
      (SETQ XYZX (CONS 10 nivel))
      (SETQ XYZX2 (CONS 11 nivel))
      (SETQ TEXTX (CONS 1 CLMUN))
      (ENTMAKE (LIST '(0 . "TEXT") '(100 . "AcDbEntity") layert '(100 . "AcDbText") XYZX tamanot TEXTX '(7 . "TIMES") '(72 . 2) xyzx2 '(73 . 0)))
    )
  )
  (IF (= OPCION "A")  
;    (if (= (getvar "acadver") "17.1s (LMS Tech)")
;      (COMMAND "INSERT" (STRCAT RUTA "BLOCKS\\ESCALAG.dwg") (STRCAT (RTOS (- X (* ESCALA 7.5956)) 2 4) "," (RTOS (+ Y (* ESCALA 21.6865)) 2 4)) ESCALA "" "")
      (COMMAND "INSERT" (STRCAT RUTA "BLOCKS\\ESCALAG.dwg") (STRCAT (RTOS (- X (* ESCALA 7.5956)) 2 4) "," (RTOS (+ Y (* ESCALA 21.6865)) 2 4)) ESCALA "" "" "" "" "" "" "" "")
;    )
;    (if (= (getvar "acadver") "17.1s (LMS Tech)")
;      (COMMAND "INSERT" (STRCAT RUTA "BLOCKS\\ESCALAG.dwg") (STRCAT (RTOS (- X (* ESCALA 7.5956)) 2 4) "," (RTOS (+ Y (* ESCALA 23.936)) 2 4)) ESCALA "" "")
      (COMMAND "INSERT" (STRCAT RUTA "BLOCKS\\ESCALAG.dwg") (STRCAT (RTOS (- X (* ESCALA 7.5956)) 2 4) "," (RTOS (+ Y (* ESCALA 23.936)) 2 4)) ESCALA "" "")
;    )
  )
  (COMMAND "CHANGE" (ENTLAST) "" "P" "LA" "PP" "")
  (SETQ EAREAS (ENTLAST))
  (setq bl (entnext EAREAS))
  (COMMAND "attedit" "" "" "" "" bl "V" "R" (RTOS (* 3 ESCALA) 2 0) "")
  (setq bl (entnext BL))
  (COMMAND "attedit" "" "" "" "" bl "V" "R" (RTOS (/ (* 3 ESCALA) 3) 2 0) "")
  (setq bl (entnext BL))
  (COMMAND "attedit" "" "" "" "" bl "V" "R" (RTOS (* 2 (/ (* ESCALA 3) 3)) 2 0) "")  
  (setq bl (entnext BL))
  (COMMAND "attedit" "" "" "" "" bl "V" "R" (RTOS (* 3 ESCALA) 2 0) "")
  (setq bl (entnext BL))
  (COMMAND "attedit" "" "" "" "" bl "V" "R" (RTOS (* 100 ESCALA) 2 0) "")
  (setq enteji poli)
  (setq entclin (car (entsel "\n Selecciona la clinica: ")))

;  (PROMPT "SELECCIONA LOS POLIGONOS DEL EJIDO Y LA CLINICA ")
;  (setq gpoCLINEJID (ssget))
;  (SETQ EX1 (SSNAME gpoCLINEJID 0))
;  (SETQ EX2 (SSNAME gpoCLINEJID 1))
  (COMMAND "AREA" "E" enteji)
  (SETQ SUPeji (RTOS (GETVAR "AREA") 2 3))
  (COMMAND "AREA" "E" entclin)
  (SETQ supclin (RTOS (GETVAR "AREA") 2 3))
;  (IF (> (ATOF SUPEX1) (ATOF SUPEX2))
;    (PROGN
;      (SETQ ENTCLIN EX2)
;      (SETQ SUPCLIN SUPEX2)
;      (SETQ ENTEJI EX1)
;      (SETQ SUPEJI SUPEX1)
;    )
;  )
;  (IF (> (ATOF SUPEX2) (ATOF SUPEX1))
;    (PROGN
;      (SETQ ENTCLIN EX1)
;      (SETQ SUPCLIN SUPEX1)
;      (SETQ ENTEJI EX2)
;      (SETQ SUPEJI SUPEX2)
;    )
;  )
  (IF (= OPCION "A") ;croquiz
    (progn 
      (command "copy" enteji "" "0,0" "0,0")
      (if (< (/ (- ymayor ymenor) (- xmayor xmenor)) 0.92857)
        (command "scale" (entlast) "" (strcat (rtos xmenor) "," (rtos ymenor)) "r" (strcat (rtos xmenor) "," (rtos ymenor)) (strcat (rtos xmayor) "," (rtos ymenor)) (* escala 5))  
        (command "scale" (entlast) "" (strcat (rtos xmenor) "," (rtos ymenor)) "r" (strcat (rtos xmenor) "," (rtos ymenor)) (strcat (rtos xmenor) "," (rtos ymayor)) (* escala 4))  
      )
      (command "move" (entlast) "" (strcat (rtos xmenor) "," (rtos ymenor)) (strcat (rtos (+ x (* escala -10.2005))) "," (rtos (+ y (* escala 25.0315)))))
      (command "copy" "p" "" (strcat (rtos (+ x (* escala -10.2005))) "," (rtos (+ y (* escala 25.0315)))) (strcat (rtos (+ x (* escala -10.2005))) "," (rtos (+ y (* escala 31)))))
    )
    (progn 
      (command "copy" enteji "" "0,0" "0,0")
      (if (< (/ (- ymayor ymenor) (- xmayor xmenor)) 0.92857)
        (command "scale" (entlast) "" (strcat (rtos xmenor) "," (rtos ymenor)) "r" (strcat (rtos xmenor) "," (rtos ymenor)) (strcat (rtos xmayor) "," (rtos ymenor)) (* escala 5))  
        (command "scale" (entlast) "" (strcat (rtos xmenor) "," (rtos ymenor)) "r" (strcat (rtos xmenor) "," (rtos ymenor)) (strcat (rtos xmenor) "," (rtos ymayor)) (* escala 4))  
      )
      (command "move" (entlast) "" (strcat (rtos xmenor) "," (rtos ymenor)) (strcat (rtos (+ x (* escala -10.3972))) "," (rtos (+ y (* escala 30.92)))))
    )
  )

  (SETQ XMENOR (+ X (* -100.0006 ESCALA)))
  (SETQ YMENOR (+ Y (* 3.9994 ESCALA)))
  (SETQ XMAYOR (+ X (* -15.9994 ESCALA)))
  (SETQ YMAYOR (+ Y (* 82.0006 ESCALA)))
  (SETQ NIVEL (LIST (+ X (* ESCALA -100.0759)) (+ y (* ESCALA 4.0453)) 0))         ;esquina inferior izquierda
  (SETQ XYZX (CONS 10 nivel))
  (SETQ XYZX2 (CONS 11 nivel))
  (setq tamanot (cons 40 (* ESCALA 0.1)))
  (setq layert (cons 8 "PP"))                            
  (setq cadenaxx (strcat (RTOS ymenor 2 0) "m. Y"))
  (SETQ TEXTX (CONS 1 cadenaxx))
  (ENTMAKE (LIST '(0 . "TEXT") '(100 . "AcDbEntity") layert '(370 . 25) '(100 . "AcDbText") XYZX tamanot TEXTX '(50 . 1.5708) '(7 . "romans") '(72 . 0) xyzx2 '(73 . 0)))
  (SETQ NIVEL (LIST (+ X (* ESCALA -99.9759)) (+ y (* ESCALA 3.85)) 0))         ;esquina inferior izquierda
  (SETQ XYZX (CONS 10 nivel))
  (SETQ XYZX2 (CONS 11 nivel))
  (setq layert (cons 8 "PP"))                            
  (setq cadenaxx (strcat (RTOS xmenor 2 0) "m. X"))
  (SETQ TEXTX (CONS 1 cadenaxx))
  (ENTMAKE (LIST '(0 . "TEXT") '(100 . "AcDbEntity") layert '(370 . 25) '(100 . "AcDbText") XYZX tamanot TEXTX '(7 . "romans") '(72 . 0) xyzx2 '(73 . 0)))
  (SETQ SEPRET (* 10 ESCALA))
  (SETQ NX (/ (- XMAYOR XMENOR) SEPRET))
  (SETQ NY (/ (- YMAYOR YMENOR) SEPRET))
  (SETQ XINI (RTOS (/ XMENOR SEPRET) 2 0))
  (IF (< (* SEPRET (ATOI XINI)) XMENOR) (SETQ XINI (RTOS (+ (ATOI XINI) 1) 2 0)))
  (SETQ YINI (RTOS (/ YMENOR SEPRET) 2 0))
  (IF (< (* SEPRET (ATOI YINI)) YMENOR) (SETQ YINI (RTOS (+ (ATOI YINI) 1) 2 0)))
  (SETQ XFIN (RTOS (/ XMAYOR SEPRET) 2 0))
  (IF (> (* SEPRET (ATOI XFIN)) XMAYOR) (SETQ XFIN (RTOS (- (ATOI XFIN) 1) 2 0)))
  (SETQ YFIN (RTOS (/ YMAYOR SEPRET) 2 0))
  (IF (> (* SEPRET (ATOI YFIN)) YMAYOR) (SETQ YFIN (RTOS (- (ATOI YFIN) 1) 2 0)))
;  (COMMAND "LINE" (STRCAT (RTOS (* SEPRET (ATOI XINI)) 2 0) "," (RTOS (* SEPRET (ATOF YINI)) 2 0)) (STRCAT (RTOS (* SEPRET (ATOF XFIN)) 2 0) "," (RTOS (* SEPRET (ATOF YFIN)) 2 0)) "")
  (SETQ XYZ (STRCAT (RTOS (* (ATOI XINI) SEPRET) 2 5) "," (RTOS (* (ATOI YINI) SEPRET) 2 5)))
  (SETQ CONT2 0)
  (REPEAT (- (ATOI XFIN) (ATOI XINI) -1)
   (SETQ CONT1 0)
   (REPEAT (- (ATOI YFIN) (ATOI YINI) -1)
    (SETQ XYZ (STRCAT (RTOS (* (+ (ATOI XINI) CONT2) SEPRET) 2 5) "," (RTOS (* (+ (ATOI YINI) CONT1) SEPRET) 2 5)))
;    (if (= (getvar "acadver") "17.1s (LMS Tech)")
;      (COMMAND "INSERT" (STRCAT RUTA "BLOCKS\\CRUSUTM2.dwg") XYZ ESCALA "")
      (COMMAND "INSERT" (STRCAT RUTA "BLOCKS\\CRUSUTM2.dwg") XYZ ESCALA "" "")
;    )
    (COMMAND "CHANGE" (ENTLAST) "" "P" "LA" "PP" "")
    (IF (= CONT2 0) 
      (PROGN
        (SETQ NIVEL (LIST (+ X (* ESCALA -100.29)) (* (+ (ATOI YINI) CONT1) SEPRET) 0))         ;0.279
        (SETQ XYZX (CONS 10 nivel))
        (SETQ XYZX2 (CONS 11 nivel))
        (setq tamanot (cons 40 (* ESCALA 0.25)))
        (setq layert (cons 8 "PP"))                            
        (SETQ TEXTX (CONS 1 (RTOS (* (+ (ATOI YINI) CONT1) SEPRET) 2 0)))
        (ENTMAKE (LIST '(0 . "TEXT") '(100 . "AcDbEntity") layert '(370 . 25) '(100 . "AcDbText") XYZX tamanot TEXTX '(7 . "romans") '(72 . 2) xyzx2 '(73 . 2)))
        (setq valorx (cons 6  "bylayer"))
        (setq punretx (cons 10 (list (+ X (* ESCALA -100)) (* (+ (ATOI YINI) CONT1) SEPRET) 0)))
        (setq punretx2 (cons 11 (list (+ X (* ESCALA -100.15)) (* (+ (ATOI YINI) CONT1) SEPRET) 0)))
        (setq layersec (cons 8 "PP"))
        (ENTMAKE (LIST '(0 . "LINE") '(100 . "AcDbEntity") layersec '(370 . 25) valorx '(100 . "AcDbLine") PUNRETX PUNRETX2))
        (SETQ NIVEL (LIST (+ X (* ESCALA -15.80)) (* (+ (ATOI YINI) CONT1) SEPRET) 0))         ;0.279
        (SETQ XYZX (CONS 10 nivel))
        (SETQ XYZX2 (CONS 11 nivel))
        (setq tamanot (cons 40 (* ESCALA 0.25)))
        (setq layert (cons 8 "PP"))                            
        (SETQ TEXTX (CONS 1 (RTOS (* (+ (ATOI YINI) CONT1) SEPRET) 2 0)))
        (ENTMAKE (LIST '(0 . "TEXT") '(100 . "AcDbEntity") layert '(370 . 25) '(100 . "AcDbText") XYZX tamanot TEXTX '(7 . "romans") '(72 . 0) xyzx2 '(73 . 2)))
        (setq valorx (cons 6  "bylayer"))
        (setq punretx (cons 10 (list (+ X (* ESCALA -16)) (* (+ (ATOI YINI) CONT1) SEPRET) 0)))
        (setq punretx2 (cons 11 (list (+ X (* ESCALA -15.85)) (* (+ (ATOI YINI) CONT1) SEPRET) 0)))
        (setq layersec (cons 8 "PP"))
        (ENTMAKE (LIST '(0 . "LINE") '(100 . "AcDbEntity") layersec '(370 . 25) valorx '(100 . "AcDbLine") PUNRETX PUNRETX2))
      )
    )
    (IF (= CONT1 0) 
      (PROGN
        (SETQ NIVEL (LIST (* (+ (ATOI XINI) CONT2) SEPRET) (+ Y (* ESCALA 82.3139))))         ;0.279
        (SETQ XYZX (CONS 10 nivel))
        (SETQ XYZX2 (CONS 11 nivel))
        (setq tamanot (cons 40 (* ESCALA 0.25)))
        (setq layert (cons 8 "PP"))                            
        (SETQ TEXTX (CONS 1 (RTOS (* (+ (ATOI XINI) CONT2) SEPRET) 2 0)))
        (ENTMAKE (LIST '(0 . "TEXT") '(100 . "AcDbEntity") layert '(370 . 25) '(100 . "AcDbText") XYZX tamanot TEXTX '(7 . "romans") '(72 . 1) xyzx2 '(73 . 1)))
        (setq valorx (cons 6  "bylayer"))
        (setq punretx (cons 10 (list (* (+ (ATOI XINI) CONT2) SEPRET) (+ Y (* ESCALA 82)) 0)))
        (setq punretx2 (cons 11 (list (* (+ (ATOI XINI) CONT2) SEPRET) (+ Y (* ESCALA 82.15)) 0)))
        (setq layersec (cons 8 "PP"))
        (ENTMAKE (LIST '(0 . "LINE") '(100 . "AcDbEntity") layersec '(370 . 25) valorx '(100 . "AcDbLine") PUNRETX PUNRETX2))
        (SETQ NIVEL (LIST (* (+ (ATOI XINI) CONT2) SEPRET) (+ Y (* ESCALA 3.3047))))         ;0.279
        (SETQ XYZX (CONS 10 nivel))
        (SETQ XYZX2 (CONS 11 nivel))
        (setq tamanot (cons 40 (* ESCALA 0.25)))
        (setq layert (cons 8 "PP"))                            
        (SETQ TEXTX (CONS 1 (RTOS (* (+ (ATOI XINI) CONT2) SEPRET) 2 0)))
        (ENTMAKE (LIST '(0 . "TEXT") '(100 . "AcDbEntity") layert '(370 . 25) '(100 . "AcDbText") XYZX tamanot TEXTX '(7 . "romans") '(72 . 1) xyzx2 '(73 . 1)))
        (setq valorx (cons 6  "bylayer"))
        (setq punretx (cons 10 (list (* (+ (ATOI XINI) CONT2) SEPRET) (+ Y (* ESCALA 4)) 0)))
        (setq punretx2 (cons 11 (list (* (+ (ATOI XINI) CONT2) SEPRET) (+ Y (* ESCALA 3.85)) 0)))
        (setq layersec (cons 8 "PP"))
        (ENTMAKE (LIST '(0 . "LINE") '(100 . "AcDbEntity") layersec '(370 . 25) valorx '(100 . "AcDbLine") PUNRETX PUNRETX2))
      )
    )
    (SETQ CONT1 (1+ CONT1))
   )
   (SETQ CONT2 (1+ CONT2))
  )
  (SETQ XVINICIAL X)
  (SETQ YVINICIAL Y)
  (C:LIBRERIA "UTM-GEO")
  (C:LIBRERIA "GEO-UTM")
  (C:LIBRERIA "DECIMALTOSEXAGESIMAL")
  (if (= zona nil) (setq zona 0))
  (SETQ zonah1 (GETint (strcat "\n ZONA UTM HORARIA <" (itoa zona) ">:")))
  (IF (/= zonah1 nil)
    (SETQ zona zonah1)
  )
  (if (= npejid nil) (setq npejid "1/1"))
  (SETQ npejid2 (GETSTRING (strcat "\n NUMERO DE POLIGONO EJIDAL <" npejid ">:")))
  (IF (/= npejid2 "")
    (SETQ npejid npejid2)
  )
  (IF (/= OPCION "A")
    (progn
      (SETQ NIVEL (LIST (- X (* ESCALA 8.7113)) (+ Y (* ESCALA 27.6365)) 0))         ;0.279
      (SETQ NIVEL2 (LIST (- X (* ESCALA 3.16)) (+ Y (* ESCALA 67.6515)) 0))         ;0.279
    )
    (progn
      (SETQ NIVEL (LIST (- X (* ESCALA 8.7113)) (+ Y (* ESCALA 23.4552)) 0))         ;0.279
      (SETQ NIVEL2 (LIST (- X (* ESCALA 3.16)) (+ Y (* ESCALA 67.6515)) 0))         ;0.279
    )
  )
  (SETQ XYZX (CONS 10 nivel))
  (SETQ XYZX2 (CONS 11 nivel))
  (SETQ TEXTX (CONS 1 (ITOA ZONA)))
  (ENTMAKE (LIST '(0 . "TEXT") '(100 . "AcDbEntity") layert '(100 . "AcDbText") XYZX tamanot TEXTX '(7 . "TIMES") '(72 . 0) xyzx2 '(73 . 0)));texto de zona h
  (SETQ XYZX (CONS 10 nivel2))
  (SETQ XYZX2 (CONS 11 nivel2))
  (SETQ TEXTX (CONS 1 npejid))
  (ENTMAKE (LIST '(0 . "TEXT") '(100 . "AcDbEntity") layert '(100 . "AcDbText") XYZX tamanot TEXTX '(7 . "TIMES") '(72 . 2) xyzx2 '(73 . 0)));texto de poligono ejidal
  (IF (= ESCALA 1) (SETQ SEPRET 0.6000000))                              ;separacion de la reticula geodesica
  (IF (= ESCALA 2.5) (SETQ SEPRET 1.5000000))
  (IF (= ESCALA 5) (SETQ SEPRET 3.000000))
  (IF (= ESCALA 10) (SETQ SEPRET 6.000000))
  (IF (= ESCALA 20) (SETQ SEPRET 12.000000))
  (IF (= ESCALA 25) (SETQ SEPRET 15.000000))
  (IF (= ESCALA 50) (SETQ SEPRET 30.000000))
  (IF (= ESCALA 100) (SETQ SEPRET 60.000000))
  (IF (= ESCALA 200) (SETQ SEPRET 120.000000))
  (IF (= ESCALA 400) (SETQ SEPRET 240.000000))
  (IF (= ESCALA 500) (SETQ SEPRET 300.000000))
  (IF (= ESCALA 1000) (SETQ SEPRET 600.000000))
  (IF (= ESCALA 1250) (SETQ SEPRET 750.000000))
  (IF (= ESCALA 1500) (SETQ SEPRET 900.000000))
  (IF (= ESCALA 1750) (SETQ SEPRET 1050.000000))
  (IF (= ESCALA 2000) (SETQ SEPRET 1200.000000))
  (SETQ SEPRET (/ (/ SEPRET 60) 60))
  (SETQ PUNTOX PTO)
  (SETQ XV (ATOF (RTOS (CadR puntoX) 2 12)))
  (SETQ YV (ATOF (RTOS (CADdR puntoX) 2 12)))
  (SETQ PUNTO (LIST (+ XMAYOR (* 2 escala)) (+ YMAYOR (* 2 escala))))
  (SETQ PUNTO2 (LIST (- XMENOR (* 2 escala)) (- YMENOR (* 2 escala))))
  (SETQ PUNTOGEO (UTM-GEO PUNTO ZONA))
  (SETQ LAT (CAR puntoGEO))
  (SETQ LONG (CADR puntoGEO))
  (SETQ PUNTOGEO2 (UTM-GEO PUNTO2 ZONA))
  (SETQ LAT2 (CAR puntoGEO2))
  (SETQ LONG2 (CADR puntoGEO2))
  (SETQ LATINI (RTOS (ABS (/ LAT2 SEPRET)) 2 0))
  (SETQ LONGINI (RTOS (ABS (/ LONG2 SEPRET)) 2 0))
  (SETQ LATFIN (RTOS (ABS (/ LAT SEPRET)) 2 0))
  (SETQ LONGFIN (RTOS (ABS (/ LONG SEPRET)) 2 0))
  (SETQ NIVEL (LIST (+ Xv (* ESCALA -100.2759)) (+ yv (* ESCALA 4.0181)) 0))         ;esquina inferior izquierda
  (setq tamanot (cons 40 (* ESCALA 0.1)))
  (SETQ XYZX (CONS 10 nivel))
  (SETQ XYZX2 (CONS 11 nivel))
  (setq layert (cons 8 "PP"))                            
  (setq cadenaxx (DECSEXA long2))
  (SETQ TEXTX (CONS 1 cadenaxx))
  (ENTMAKE (LIST '(0 . "TEXT") '(100 . "AcDbEntity") layert '(370 . 25) '(100 . "AcDbText") XYZX tamanot TEXTX '(7 . "romans") '(72 . 2) xyzx2 '(73 . 0)))
  (SETQ NIVEL (LIST (+ Xv (* ESCALA -99.9759)) (+ yv (* ESCALA 3.63)) 0))         ;esquina inferior izquierda
  (SETQ XYZX (CONS 10 nivel))
  (SETQ XYZX2 (CONS 11 nivel))
  (setq layert (cons 8 "PP"))                            
  (setq cadenaxx (DECSEXA (* lat2 -1)))
  (SETQ TEXTX (CONS 1 cadenaxx))
  (ENTMAKE (LIST '(0 . "TEXT") '(100 . "AcDbEntity") layert '(370 . 25) '(100 . "AcDbText") XYZX tamanot TEXTX '(7 . "romans") '(72 . 0) xyzx2 '(73 . 0)))
;  (SETQ PUNTO (LIST (- (+ XMAYOR (* 0.5 ESCALA)) (* 100.55 ESCALA)) YMAYOR))
;  (SETQ PUNTOGEO (UTM-GEO PUNTO ZONA))
;  (SETQ LAT (CAR puntoGEO))

  (SETQ CONT2 0)
  (REPEAT (- (ATOI LATini) (ATOI LATfin))
   (SETQ CONT1 0)
   (REPEAT (- (ATOI LATini) (ATOI LATfin))
    (SETQ PGEO (LIST (* (- (ATOI LATINI) CONT2) SEPRET -1) (* (+ (ATOI LONGINI) CONT1) SEPRET)))
    (SETQ XYZ (GEO-UTM PGEO))
;    (if (= (getvar "acadver") "17.1s (LMS Tech)")
;      (COMMAND "INSERT" (STRCAT RUTA "BLOCKS\\CRUZGPS.dwg") XYZ ESCALA "")
      (COMMAND "INSERT" (STRCAT RUTA "BLOCKS\\CRUZGPS.dwg") XYZ ESCALA "" "")
;    )
    (COMMAND "CHANGE" (ENTLAST) "" "P" "LA" "PP" "")
    (IF (= CONT2 0) 
      (PROGN
        (SETQ PGEO (LIST LAT (* (+ (ATOI LONGINI) CONT1) SEPRET)))
        (SETQ XYZ3 (GEO-UTM PGEO))
        (SETQ PGEO (LIST LAT2 (* (+ (ATOI LONGINI) CONT1) SEPRET)))
        (SETQ XYZ2 (GEO-UTM PGEO))
        (SETQ NIVEL (LIST (+ XMAYOR (* 0.5 ESCALA)) (CADR XYZ3) 0))         ;0.279
        (SETQ XYZX (CONS 10 nivel))
        (SETQ XYZX2 (CONS 11 nivel))
        (setq tamanot (cons 40 (* ESCALA 0.15)))
        (setq layert (cons 8 "PP"))                            
        (SETQ TEXTX (CONS 1 (DECSEXA (* (+ (ATOI LONGINI) CONT1) SEPRET))))
        (ENTMAKE (LIST '(0 . "TEXT") '(100 . "AcDbEntity") layert '(370 . 25) '(100 . "AcDbText") XYZX tamanot TEXTX '(7 . "romans") '(72 . 0) xyzx2 '(73 . 1)))
        (SETQ NIVEL (LIST (- XMENOR (* 0.5 ESCALA)) (CADR XYZ2) 0))         ;0.279
        (SETQ XYZX (CONS 10 nivel))
        (SETQ XYZX2 (CONS 11 nivel))
        (setq tamanot (cons 40 (* ESCALA 0.15)))
        (setq layert (cons 8 "PP"))                            
        (SETQ TEXTX (CONS 1 (DECSEXA (* (+ (ATOI LONGINI) CONT1) SEPRET))))
        (ENTMAKE (LIST '(0 . "TEXT") '(100 . "AcDbEntity") layert '(370 . 25) '(100 . "AcDbText") XYZX tamanot TEXTX '(7 . "romans") '(72 . 2) xyzx2 '(73 . 1)))
      )
    )
    (IF (= CONT1 0) 
      (PROGN
        (SETQ PGEO (LIST (* (- (ATOI LATINI) CONT2) SEPRET -1) LONG))
        (SETQ XYZ3 (GEO-UTM PGEO))
        (SETQ PGEO (LIST (* (- (ATOI LATINI) CONT2) SEPRET -1) LONG2))
        (SETQ XYZ2 (GEO-UTM PGEO))
        (SETQ NIVEL (LIST (CAR XYZ3) (+ YMAYOR (* 0.8 ESCALA)) 0))         ;0.279
        (SETQ XYZX (CONS 10 nivel))
        (SETQ XYZX2 (CONS 11 nivel))
        (setq tamanot (cons 40 (* ESCALA 0.15)))
        (setq layert (cons 8 "PP"))                            
        (SETQ TEXTX (CONS 1 (DECSEXA (* (- (ATOI LATINI) CONT2) SEPRET))))
        (ENTMAKE (LIST '(0 . "TEXT") '(100 . "AcDbEntity") layert '(370 . 25) '(100 . "AcDbText") XYZX tamanot TEXTX '(7 . "romans") '(72 . 1) xyzx2 '(73 . 1)))
        (SETQ NIVEL (LIST (CAR XYZ2) (- YMENOR (* 1 ESCALA)) 0))         ;0.279
        (SETQ XYZX (CONS 10 nivel))
        (SETQ XYZX2 (CONS 11 nivel))
        (setq tamanot (cons 40 (* ESCALA 0.15)))
        (setq layert (cons 8 "PP"))                            
        (SETQ TEXTX (CONS 1 (DECSEXA (* (- (ATOI LATINI) CONT2) SEPRET))))
        (ENTMAKE (LIST '(0 . "TEXT") '(100 . "AcDbEntity") layert '(370 . 25) '(100 . "AcDbText") XYZX tamanot TEXTX '(7 . "romans") '(72 . 1) xyzx2 '(73 . 1)))
      )
    )
    (SETQ CONT1 (1+ CONT1))
   )
   (SETQ CONT2 (1+ CONT2))
  )
  (IF (= OPCION "A")                                                                                              ;superficies de ejidos
    (PROGN 
      (SETQ NIVEL (LIST (- XVINICIAL (* ESCALA 16.6643)) (+ YVINICIAL (* ESCALA 13.7693)) 0))         ;0.279
      (SETQ XYZX (CONS 10 nivel))
      (SETQ XYZX2 (CONS 11 nivel))
      (setq tamanot (cons 40 (* ESCALA 0.25)))
      (setq layert (cons 8 "PP"))                            
      (SETQ TEXTX (CONS 1 (MTOH SUPEJI)))
      (ENTMAKE (LIST '(0 . "TEXT") '(100 . "AcDbEntity") layert '(100 . "AcDbText") XYZX tamanot TEXTX '(41 . 0.75) '(7 . "romand") '(72 . 2) xyzx2 '(73 . 1)))
      (SETQ NIVEL (LIST (- XVINICIAL (* ESCALA 16.6643)) (+ YVINICIAL (* ESCALA 12.0036)) 0))         ;0.279
      (SETQ XYZX (CONS 10 nivel))
      (SETQ XYZX2 (CONS 11 nivel))
      (setq tamanot (cons 40 (* ESCALA 0.25)))
      (setq layert (cons 8 "PP"))                            
      (SETQ TEXTX (CONS 1 (MTOH SUPCLIN)))
      (ENTMAKE (LIST '(0 . "TEXT") '(100 . "AcDbEntity") layert '(100 . "AcDbText") XYZX tamanot TEXTX '(41 . 0.75) '(7 . "romand") '(72 . 2) xyzx2 '(73 . 1)))
      (SETQ NIVEL (LIST (- XVINICIAL (* ESCALA 16.6643)) (+ YVINICIAL (* ESCALA 5.6327)) 0))         ;0.279
      (SETQ XYZX (CONS 10 nivel))
      (SETQ XYZX2 (CONS 11 nivel))
      (setq tamanot (cons 40 (* ESCALA 0.25)))
      (setq layert (cons 8 "PP"))                            
      (SETQ TEXTX (CONS 1 (MTOH SUPEJI)))
      (ENTMAKE (LIST '(0 . "TEXT") '(100 . "AcDbEntity") layert '(100 . "AcDbText") XYZX tamanot TEXTX '(41 . 0.75) '(7 . "romand") '(72 . 2) xyzx2 '(73 . 1)))
      (SETQ NIVEL (LIST (- XVINICIAL (* ESCALA 16.6643)) (+ YVINICIAL (* ESCALA 9.3923)) 0))         ;0.279
      (SETQ XYZX (CONS 10 nivel))
      (SETQ XYZX2 (CONS 11 nivel))
      (setq tamanot (cons 40 (* ESCALA 0.25)))
      (setq layert (cons 8 "PP"))                            
      (SETQ TEXTX (CONS 1 (MTOH (RTOS (- (ATOF SUPEJI) (ATOF SUPCLIN)) 2 5))))
      (ENTMAKE (LIST '(0 . "TEXT") '(100 . "AcDbEntity") layert '(100 . "AcDbText") XYZX tamanot TEXTX '(41 . 0.75) '(7 . "romand") '(72 . 2) xyzx2 '(73 . 1)))
      (C:LIBRERIA "acota")
      (acotax enteji (* 0.15 escala))
      (acotax entclin (* 0.15 escala))
;      (SETQ NIVEL (LIST (- XVINICIAL (* ESCALA 16.6643)) (+ YVINICIAL (* ESCALA 5.3506)) 0))         ;0.279
;      (SETQ XYZX (CONS 10 nivel))
;      (SETQ XYZX2 (CONS 11 nivel))
;      (setq tamanot (cons 40 (* ESCALA 0.25)))
;      (setq layert (cons 8 "PP"))                            
;      (SETQ TEXTX (CONS 1 (MTOH SUPEJI)))
;      (ENTMAKE (LIST '(0 . "TEXT") '(100 . "AcDbEntity") layert '(100 . "AcDbText") XYZX tamanot TEXTX '(41 . 0.75) '(7 . "romand") '(72 . 2) xyzx2 '(73 . 1)))
    )
    (PROGN 
      (SETQ NIVEL (LIST (- XVINICIAL (* ESCALA 17.168)) (+ YVINICIAL (* ESCALA 11.9418)) 0))         ;0.279
      (SETQ XYZX (CONS 10 nivel))
      (SETQ XYZX2 (CONS 11 nivel))
      (setq tamanot (cons 40 (* ESCALA 0.25)))
      (setq layert (cons 8 "PP"))                            
      (SETQ TEXTX (CONS 1 (MTOH SUPEJI)))
      (ENTMAKE (LIST '(0 . "TEXT") '(100 . "AcDbEntity") layert '(100 . "AcDbText") XYZX tamanot TEXTX '(41 . 0.7) '(7 . "romand") '(72 . 2) xyzx2 '(73 . 1)))
      (SETQ NIVEL (LIST (- XVINICIAL (* ESCALA 17.168)) (+ YVINICIAL (* ESCALA 8.9584)) 0))         ;0.279
      (SETQ XYZX (CONS 10 nivel))
      (SETQ XYZX2 (CONS 11 nivel))
      (setq tamanot (cons 40 (* ESCALA 0.25)))
      (setq layert (cons 8 "PP"))                            
      (SETQ TEXTX (CONS 1 (MTOH SUPEJI)))
      (ENTMAKE (LIST '(0 . "TEXT") '(100 . "AcDbEntity") layert '(100 . "AcDbText") XYZX tamanot TEXTX '(41 . 0.7) '(7 . "romand") '(72 . 2) xyzx2 '(73 . 1)))
      (SETQ NIVEL (LIST (- XVINICIAL (* ESCALA 17.168)) (+ YVINICIAL (* ESCALA 5.4608)) 0))         ;0.279
      (SETQ XYZX (CONS 10 nivel))
      (SETQ XYZX2 (CONS 11 nivel))
      (setq tamanot (cons 40 (* ESCALA 0.25)))
      (setq layert (cons 8 "PP"))                            
      (SETQ TEXTX (CONS 1 (MTOH SUPEJI)))
      (ENTMAKE (LIST '(0 . "TEXT") '(100 . "AcDbEntity") layert '(100 . "AcDbText") XYZX tamanot TEXTX '(41 . 0.7) '(7 . "romand") '(72 . 2) xyzx2 '(73 . 1)))
    )
  )
)

(defun ppchico ()
  (setq punver1 (list xmenor ymenor))
  (setq punver2 (list xmayor ymayor))
  (setq escgpo (ssget "C" punver1 punver2 '((0 . "INSERT"))))
  (if (= escgpo nil) 
    (progn
      (alert "faltan vertices de la clinica")
      (exit)
    )
  )
  (setq ej (ssname escgpo 0))
  (setq t1 1)
  (while Ej
    (setq fs2 (cdr (assoc 41 (entget ej))))
    (setq FSN (/ (* escala 0.2) FS2))
    (setq XYZ (cdr (assoc 10 (entget Ej))))
      (if (= "PUNTO" (cdr (assoc 2 (entget Ej))))
        (command "SCALE" (cdr (assoc -1 (entget Ej))) "" XYZ fsn)
      )
      (setq Ej (ssname escgpo t1))
      (setq t1 (1+ t1))
  )
;  (SETQ OPCION (GETSTRING "\n PP de solar o plano general (s/r) <r>"))
;  (if (= opcion "") (setq opcion "r"))
  (SETQ OPCION (STRCASE TIPOPLANO))
  (if (= (strcase opcion) "S") (setq nblock "pPINEGI2.dwg") (setq nblock "pPINEGI3.dwg"))
  (setq opcion (strcase TIPOPLANO))
  (SETQ CENTROIDEY1 (+ (/ (- YMAYOR YMENOR) 2) YMENOR))
  (SETQ CENTROIDEX1 (+ (/ (- XMAYOR XMENOR) 2) XMENOR))
  (SETQ Y (- CENTROIDEY1 (* ESCALA 8.3164)))
  (SETQ X (+ CENTROIDEX1 (* ESCALA 9.7739)))
;  (if (= (getvar "acadver") "17.1s (LMS Tech)")
;    (COMMAND "INSERt" (STRCAT RUTA "BLOCKS\\" nblock) "s" ESCALA (strcat (rtos x 2 6) "," (rtos y 2 6)) "")
    (COMMAND "INSERt" (STRCAT RUTA "BLOCKS\\" nblock) ESCALA (strcat (rtos x 2 6) "," (rtos y 2 6)) ESCALA "" "")
;  )
  (setq PTO (CONS 10 (LIST X Y 0)))
  (SETQ Yv (CADR PTO))
  (SETQ Xv (CAR PTO))
  (COMMAND "EXPLODE" (ENTLAST) "")
;  (COMMAND "CHANGE" "P" "" "P" "LA" "PP" "")
  (IF (= NOMMUN NIL) (SETQ NOMMUN "X"))
  (SETQ NOMMUN1 (STRCASE (GETSTRING PROMPT (STRCAT "\n NOMBRE DEL MUNICIPIO <" NOMMUN ">:"))))
  (IF (/= NOMMUN1 "")
    (SETQ NOMMUN NOMMUN1)
  )
  (setq clmun (CLAVEMUNI nommun))
  (IF (= (STRLEN CLMUN) 1) (SETQ CLMUN (STRCAT "00" CLMUN)))
  (IF (= (STRLEN CLMUN) 2) (SETQ CLMUN (STRCAT "0" CLMUN)))
  (IF (= CLMUN NIL) (SETQ CLMUN "XXX"))
  (SETQ CLMUN1 (GETSTRING (STRCAT "\n CLAVE DEL MUNICIPIO <" CLMUN ">:")))
  (IF (/= CLMUN1 "")
    (SETQ CLMUN CLMUN1)
  )
  (IF (= NOMEJI NIL) (SETQ NOMEJI "X"))
  (SETQ NOMEJI1 (STRCASE (GETSTRING PROMPT (STRCAT "\n NOMBRE DEL EJIDO <" NOMEJI ">:"))))
  (IF (/= NOMEJI1 "")
    (SETQ NOMEJI NOMEJI1)
  )
  (setq CLEJI (CLAVEJIDO nomEJI CLMUN))
  (IF (= (STRLEN CLEJI) 1) (SETQ CLEJI (STRCAT "00" CLEJI)))
  (IF (= (STRLEN CLEJI) 2) (SETQ CLEJI (STRCAT "0" CLEJI)))
  (IF (= CLEJI NIL) (SETQ CLEJI "XXX"))
  (SETQ CLEJI1 (GETSTRING (STRCAT "\n CLAVE DEL EJIDO <" CLEJI ">:")))
  (IF (/= CLEJI1 "")
    (SETQ CLEJI CLEJI1)
  )
  (IF (= NOMLOC NIL) (SETQ NOMLOC "X"))
  (SETQ NOMLOC1 (STRCASE (GETSTRING PROMPT (STRCAT "\n NOMBRE DE LA LOCALIDAD <" NOMLOC ">:"))))
  (IF (/= NOMLOC1 "")
    (SETQ NOMLOC NOMLOC1)
  )
  (setq clLOC (CLAVELOCALIDAD nomLOC CLMUN))
  (IF (= (STRLEN CLLOC) 1) (SETQ CLLOC (STRCAT "000" CLLOC)))
  (IF (= (STRLEN CLLOC) 2) (SETQ CLLOC (STRCAT "00" CLLOC)))
  (IF (= (STRLEN CLLOC) 3) (SETQ CLLOC (STRCAT "0" CLLOC)))
  (IF (= CLLOC NIL) (SETQ CLLOC "XXXX"))
  (SETQ CLLOC1 (GETSTRING (STRCAT "\n CLAVE DE LA LOCALIDAD <" CLLOC ">:")))
  (IF (/= CLLOC1 "")
    (SETQ CLLOC CLLOC1)
  )
;  (setq poligonoc (car (entsel "Selecciona el poligono de la clinica")))
  (setq poligonoc poli)
  (command "AREA" "OB" poligonoc "")
  (SETQ AREAclinica (RTOS (GETVAR "AREA") 2 3))
  (if (= zona nil) (setq zona 0))
  (SETQ zonah1 (GETint (strcat "\n ZONA UTM HORARIA <" (itoa zona) ">:")))
  (IF (/= zonah1 nil)
    (SETQ zona zonah1)
  )
  (if (= npejid nil) (setq npejid "1/1"))
  (SETQ npejid2 (GETSTRING (strcat "\n NUMERO DE POLIGONO EJIDAL <" npejid ">:")))
  (IF (/= npejid2 "")
    (SETQ npejid npejid2)
  )
  (setq tamanot (cons 40 (* ESCALA 0.1272)))
  (SETQ NIVEL2 (LIST (+ X (* ESCALA 8.0705)) (+ Y (* ESCALA 11.743)) 0))         ;0.279
  (SETQ XYZX (CONS 10 nivel2))
  (SETQ XYZX2 (CONS 11 nivel2))
  (SETQ TEXTX (CONS 1 npejid))
  (setq layert (cons 8 "PP"))                            
  (ENTMAKE (LIST '(0 . "TEXT") '(100 . "AcDbEntity") layert '(100 . "AcDbText") XYZX tamanot TEXTX '(7 . "XX") '(72 . 2) xyzx2 '(73 . 0)));texto de poligono ejidal
  (IF (= (STRCASE OPCION) "P")
   (PROGN 
    (SETQ NIVEL (LIST (+ X (* ESCALA 3.0056)) (+ Y (* ESCALA 12.6556)) 0))         ;0.279
    (SETQ XYZX (CONS 10 nivel))
    (SETQ XYZX2 (CONS 11 nivel))
    (setq tamanot (cons 40 (* ESCALA 0.1272)))
    (setq layert (cons 8 "PP"))                            
    (SETQ TEXTX (CONS 1 NOMMUN))
    (ENTMAKE (LIST '(0 . "TEXT") '(100 . "AcDbEntity") layert '(100 . "AcDbText") XYZX tamanot TEXTX '(7 . "XX") '(72 . 0) xyzx2 '(73 . 0)))
    (SETQ NIVEL (LIST (+ X (* ESCALA 8.0705)) (+ Y (* ESCALA 12.6556)) 0))         ;0.279
    (SETQ XYZX (CONS 10 nivel))
    (SETQ XYZX2 (CONS 11 nivel))
    (SETQ TEXTX (CONS 1 CLMUN))
    (ENTMAKE (LIST '(0 . "TEXT") '(100 . "AcDbEntity") layert '(100 . "AcDbText") XYZX tamanot TEXTX '(7 . "XX") '(72 . 2) xyzx2 '(73 . 0)))
    (SETQ NIVEL (LIST (+ X (* ESCALA 3.0056)) (+ Y (* ESCALA 12.4784)) 0))         ;0.279
    (SETQ XYZX (CONS 10 nivel))
    (SETQ XYZX2 (CONS 11 nivel))
    (SETQ TEXTX (CONS 1 NOMEJI))
    (ENTMAKE (LIST '(0 . "TEXT") '(100 . "AcDbEntity") layert '(100 . "AcDbText") XYZX tamanot TEXTX '(7 . "XX") '(72 . 0) xyzx2 '(73 . 0)))
    (SETQ NIVEL (LIST (+ X (* ESCALA 8.0705)) (+ Y (* ESCALA 12.4784)) 0))         ;0.279
    (SETQ XYZX (CONS 10 nivel))
    (SETQ XYZX2 (CONS 11 nivel))
    (SETQ TEXTX (CONS 1 CLEJI))
    (ENTMAKE (LIST '(0 . "TEXT") '(100 . "AcDbEntity") layert '(100 . "AcDbText") XYZX tamanot TEXTX '(7 . "XX") '(72 . 2) xyzx2 '(73 . 0)))
    (SETQ NIVEL (LIST (+ X (* ESCALA 3.0056)) (+ Y (* ESCALA 10.603)) 0))         ;0.279
    (SETQ XYZX (CONS 10 nivel))
    (SETQ XYZX2 (CONS 11 nivel))
    (SETQ TEXTX (CONS 1 NOMMUN))
    (ENTMAKE (LIST '(0 . "TEXT") '(100 . "AcDbEntity") layert '(100 . "AcDbText") XYZX tamanot TEXTX '(7 . "XX") '(72 . 0) xyzx2 '(73 . 0)))
    (SETQ NIVEL (LIST (+ X (* ESCALA 8.0705)) (+ Y (* ESCALA 10.603)) 0))         ;0.279
    (SETQ XYZX (CONS 10 nivel))
    (SETQ XYZX2 (CONS 11 nivel))
    (SETQ TEXTX (CONS 1 clMUN))
    (ENTMAKE (LIST '(0 . "TEXT") '(100 . "AcDbEntity") layert '(100 . "AcDbText") XYZX tamanot TEXTX '(7 . "XX") '(72 . 2) xyzx2 '(73 . 0)))
;    (if (= (getvar "acadver") "17.1s (LMS Tech)")
;      (COMMAND "INSERT" (STRCAT RUTA "BLOCKS\\ESCALAG2.dwg") (STRCAT (RTOS (+ X (* ESCALA 4.8155)) 2 4) "," (RTOS (+ Y (* ESCALA 2.3627)) 2 4)) ESCALA "")
      (COMMAND "INSERT" (STRCAT RUTA "BLOCKS\\ESCALAG2.dwg") (STRCAT (RTOS (+ X (* ESCALA 4.8155)) 2 4) "," (RTOS (+ Y (* ESCALA 2.3627)) 2 4)) ESCALA "" "" "" "" "" "" "" "")
;    )
    (COMMAND "CHANGE" (ENTLAST) "" "P" "LA" "PP" "")
   )
  )
  (IF (/= (STRCASE OPCION) "P")
   (PROGN
    (SETQ NIVEL (LIST (+ X (* ESCALA 3.00)) (+ Y (* ESCALA 12.2791)) 0))         ;0.279
    (SETQ XYZX (CONS 10 nivel))
    (SETQ XYZX2 (CONS 11 nivel))
    (setq tamanot (cons 40 (* ESCALA 0.1272)))
    (setq layert (cons 8 "PP"))                            
    (SETQ TEXTX (CONS 1 NOMMUN))
    (ENTMAKE (LIST '(0 . "TEXT") '(100 . "AcDbEntity") layert '(100 . "AcDbText") XYZX tamanot TEXTX '(7 . "XX") '(72 . 0) xyzx2 '(73 . 0)))
    (SETQ NIVEL (LIST (+ X (* ESCALA 8.0705)) (+ Y (* ESCALA 12.2791)) 0))         ;0.279
    (SETQ XYZX (CONS 10 nivel))
    (SETQ XYZX2 (CONS 11 nivel))
    (SETQ TEXTX (CONS 1 CLMUN))
    (ENTMAKE (LIST '(0 . "TEXT") '(100 . "AcDbEntity") layert '(100 . "AcDbText") XYZX tamanot TEXTX '(7 . "XX") '(72 . 2) xyzx2 '(73 . 0)))
    (SETQ NIVEL (LIST (+ X (* ESCALA 3.00)) (+ Y (* ESCALA 12.1019)) 0))         ;0.279
    (SETQ XYZX (CONS 10 nivel))
    (SETQ XYZX2 (CONS 11 nivel))
    (SETQ TEXTX (CONS 1 NOMEJI))
    (ENTMAKE (LIST '(0 . "TEXT") '(100 . "AcDbEntity") layert '(100 . "AcDbText") XYZX tamanot TEXTX '(7 . "XX") '(72 . 0) xyzx2 '(73 . 0)))
    (SETQ NIVEL (LIST (+ X (* ESCALA 8.0705)) (+ Y (* ESCALA 12.1019)) 0))         ;0.279
    (SETQ XYZX (CONS 10 nivel))
    (SETQ XYZX2 (CONS 11 nivel))
    (SETQ TEXTX (CONS 1 CLEJI))
    (ENTMAKE (LIST '(0 . "TEXT") '(100 . "AcDbEntity") layert '(100 . "AcDbText") XYZX tamanot TEXTX '(7 . "XX") '(72 . 2) xyzx2 '(73 . 0)))
    (SETQ NIVEL (LIST (+ X (* ESCALA 3.00)) (+ Y (* ESCALA 9.992)) 0))         ;0.279
    (SETQ XYZX (CONS 10 nivel))
    (SETQ XYZX2 (CONS 11 nivel))
    (SETQ TEXTX (CONS 1 NOMMUN))
    (ENTMAKE (LIST '(0 . "TEXT") '(100 . "AcDbEntity") layert '(100 . "AcDbText") XYZX tamanot TEXTX '(7 . "XX") '(72 . 0) xyzx2 '(73 . 0)))
    (SETQ NIVEL (LIST (+ X (* ESCALA 8.0705)) (+ Y (* ESCALA 9.992)) 0))         ;0.279
    (SETQ XYZX (CONS 10 nivel))
    (SETQ XYZX2 (CONS 11 nivel))
    (SETQ TEXTX (CONS 1 CLMUN))
    (ENTMAKE (LIST '(0 . "TEXT") '(100 . "AcDbEntity") layert '(100 . "AcDbText") XYZX tamanot TEXTX '(7 . "XX") '(72 . 2) xyzx2 '(73 . 0)))
    (SETQ NIVEL (LIST (+ X (* ESCALA 3.00)) (+ Y (* ESCALA 11.553)) 0))         ;0.279
    (SETQ XYZX (CONS 10 nivel))
    (SETQ XYZX2 (CONS 11 nivel))
    (SETQ TEXTX (CONS 1 NOMLOC))
    (ENTMAKE (LIST '(0 . "TEXT") '(100 . "AcDbEntity") layert '(100 . "AcDbText") XYZX tamanot TEXTX '(7 . "XX") '(72 . 0) xyzx2 '(73 . 0)))
    (SETQ NIVEL (LIST (+ X (* ESCALA 8.0705)) (+ Y (* ESCALA 11.553)) 0))         ;0.279
    (SETQ XYZX (CONS 10 nivel))
    (SETQ XYZX2 (CONS 11 nivel))
    (SETQ TEXTX (CONS 1 CLLOC))
    (ENTMAKE (LIST '(0 . "TEXT") '(100 . "AcDbEntity") layert '(100 . "AcDbText") XYZX tamanot TEXTX '(7 . "XX") '(72 . 2) xyzx2 '(73 . 0)))
;    (if (= (getvar "acadver") "17.1s (LMS Tech)")
;      (COMMAND "INSERT" (STRCAT RUTA "BLOCKS\\ESCALAG2.dwg") (STRCAT (RTOS (+ X (* ESCALA 4.8155)) 2 4) "," (RTOS (+ Y (* ESCALA 2.3627)) 2 4)) ESCALA "")
      (COMMAND "INSERT" (STRCAT RUTA "BLOCKS\\ESCALAG2.dwg") (STRCAT (RTOS (+ X (* ESCALA 4.8155)) 2 4) "," (RTOS (+ Y (* ESCALA 2.3627)) 2 4)) ESCALA "" "" "" "" "" "" "" "")
;    )
    (COMMAND "CHANGE" (ENTLAST) "" "P" "LA" "PP" "")
   )
  )
  (SETQ EAREAS (ENTLAST))
  (setq bl (entnext EAREAS))
  (COMMAND "attedit" "" "" "" "" bl "V" "R" (RTOS (/ (* 3 ESCALA) 3) 2 0) "")
  (setq bl (entnext BL))
  (COMMAND "attedit" "" "" "" "" bl "V" "R" (RTOS (* 2 (/ (* ESCALA 3) 3)) 2 0) "")
  (setq bl (entnext BL))
  (COMMAND "attedit" "" "" "" "" bl "V" "R" (RTOS (* 3 ESCALA) 2 0) "")
  (setq bl (entnext BL))
  (COMMAND "attedit" "" "" "" "" bl "V" "R" (RTOS (* 100 ESCALA) 2 0) "")
  (setq bl (entnext BL))
  (COMMAND "attedit" "" "" "" "" bl "V" "R" (RTOS (* 3 ESCALA) 2 0) "")
  (SETQ XMENOR (+ X (* -19.4239 ESCALA))) 
  (SETQ YMENOR (+ y (* 0.0164 ESCALA)))
  (SETQ XMAYOR (+ X (* -0.1239 ESCALA)))
  (SETQ YMAYOR (+ Y (* 16.6164 ESCALA)))
  (SETQ NIVEL (LIST (+ X (* ESCALA -19.4239)) (+ y (* ESCALA 0.016)) 0))         ;esquina inferior izquierda
  (SETQ XYZX (CONS 10 nivel))
  (SETQ XYZX2 (CONS 11 nivel))
  (setq tamanot (cons 40 (* ESCALA 0.1)))
  (setq layert (cons 8 "PP"))                            
  (setq cadenaxx (strcat (RTOS ymenor 2 0) "m. Y"))
  (SETQ TEXTX (CONS 1 cadenaxx))
  (ENTMAKE (LIST '(0 . "TEXT") '(100 . "AcDbEntity") layert '(370 . 25) '(100 . "AcDbText") XYZX tamanot TEXTX '(50 . 1.5708) '(7 . "romans") '(72 . 0) xyzx2 '(73 . 0)))
  (SETQ NIVEL (LIST (+ X (* ESCALA -19.4239)) (- y (* ESCALA 0.100)) 0))         ;esquina inferior izquierda
  (SETQ XYZX (CONS 10 nivel))
  (SETQ XYZX2 (CONS 11 nivel))
  (setq layert (cons 8 "PP"))                            
  (setq cadenaxx (strcat (RTOS xmenor 2 0) "m. X"))
  (SETQ TEXTX (CONS 1 cadenaxx))
  (ENTMAKE (LIST '(0 . "TEXT") '(100 . "AcDbEntity") layert '(370 . 25) '(100 . "AcDbText") XYZX tamanot TEXTX '(7 . "romans") '(72 . 0) xyzx2 '(73 . 0)))
  (SETQ SEPRET (* ESCALA 5))
  (SETQ NX (/ (- XMAYOR XMENOR) SEPRET))
  (SETQ NY (/ (- YMAYOR YMENOR) SEPRET))
  (SETQ XINI (RTOS (/ XMENOR SEPRET) 2 0))
  (IF (< (* SEPRET (ATOI XINI)) XMENOR) (SETQ XINI (RTOS (+ (ATOI XINI) 1) 2 0)))
  (SETQ YINI (RTOS (/ YMENOR SEPRET) 2 0))
  (IF (< (* SEPRET (ATOI YINI)) YMENOR) (SETQ YINI (RTOS (+ (ATOI YINI) 1) 2 0)))
  (SETQ XFIN (RTOS (/ XMAYOR SEPRET) 2 0))
  (IF (> (* SEPRET (ATOI XFIN)) XMAYOR) (SETQ XFIN (RTOS (- (ATOI XFIN) 1) 2 0)))
  (SETQ YFIN (RTOS (/ YMAYOR SEPRET) 2 0))
  (IF (> (* SEPRET (ATOI YFIN)) YMAYOR) (SETQ YFIN (RTOS (- (ATOI YFIN) 1) 2 0)))
;  (COMMAND "LINE" (STRCAT (RTOS (* SEPRET (ATOI XINI)) 2 0) "," (RTOS (* SEPRET (ATOF YINI)) 2 0)) (STRCAT (RTOS (* SEPRET (ATOF XFIN)) 2 0) "," (RTOS (* SEPRET (ATOF YFIN)) 2 0)) "")
  (SETQ XYZ (STRCAT (RTOS (* (ATOI XINI) SEPRET) 2 5) "," (RTOS (* (ATOI YINI) SEPRET) 2 5)))
  (SETQ CONT2 0)
  (REPEAT (- (ATOI XFIN) (ATOI XINI) -1)
   (SETQ CONT1 0)
   (REPEAT (- (ATOI YFIN) (ATOI YINI) -1)
    (SETQ XYZ (STRCAT (RTOS (* (+ (ATOI XINI) CONT2) SEPRET) 2 5) "," (RTOS (* (+ (ATOI YINI) CONT1) SEPRET) 2 5)))
    (SETQ XYZ2 (STRCAT (RTOS (* (+ (ATOI XINI) CONT2) SEPRET) 2 5) "," (RTOS (+ Y (* ESCALA 16.7)) 2 5)))
    (SETQ XYZ3 (STRCAT (RTOS (+ X (* ESCALA -19.1)) 2 5) "," (RTOS (* (+ (ATOI YINI) CONT1) SEPRET) 2 5)))
    (SETQ XYZ4 (STRCAT (RTOS (* (+ (ATOI XINI) CONT2) SEPRET) 2 5) "," (RTOS (+ Y (* ESCALA 16.636)) 2 5)))
    (SETQ XYZ5 (STRCAT (RTOS (+ X (* ESCALA -19.0359)) 2 5) "," (RTOS (* (+ (ATOI YINI) CONT1) SEPRET) 2 5)))
;    (if (= (getvar "acadver") "17.1s (LMS Tech)")
;      (COMMAND "INSERT" (STRCAT RUTA "BLOCKS\\CRUSUTM.dwg") XYZ ESCALA "")
      (COMMAND "INSERT" (STRCAT RUTA "BLOCKS\\CRUSUTM.dwg") XYZ ESCALA "" "")
;    )
    (COMMAND "CHANGE" (ENTLAST) "" "P" "LA" "PP" "")
    (IF (= CONT2 0) 
      (PROGN
        (SETQ NIVEL (LIST (+ X (* ESCALA -19.4989)) (* (+ (ATOI YINI) CONT1) SEPRET) 0))         ;0.279
        (SETQ XYZX (CONS 10 nivel))
        (SETQ XYZX2 (CONS 11 nivel))
        (setq tamanot (cons 40 (* ESCALA 0.15)))
        (setq layert (cons 8 "PP"))                            
        (SETQ TEXTX (CONS 1 (RTOS (* (+ (ATOI YINI) CONT1) SEPRET) 2 0)))
        (ENTMAKE (LIST '(0 . "TEXT") '(100 . "AcDbEntity") layert '(370 . 25) '(100 . "AcDbText") XYZX tamanot TEXTX '(41 . 0.75) '(7 . "romans") '(72 . 2) xyzx2 '(73 . 2)))
        (setq valorx (cons 6  "bylayer"))
        (setq punretx (cons 10 (list (+ X (* ESCALA -19.4239)) (* (+ (ATOI YINI) CONT1) SEPRET) 0)))
        (setq punretx2 (cons 11 (list (+ X (* ESCALA -19.4989)) (* (+ (ATOI YINI) CONT1) SEPRET) 0)))
        (setq layersec (cons 8 "PP"))
        (ENTMAKE (LIST '(0 . "LINE") '(100 . "AcDbEntity") layersec '(370 . 25) valorx '(100 . "AcDbLine") PUNRETX PUNRETX2))
        (SETQ NIVEL (LIST (- X (* ESCALA 0.0489)) (* (+ (ATOI YINI) CONT1) SEPRET) 0))         ;0.279
        (SETQ XYZX (CONS 10 nivel))
        (SETQ XYZX2 (CONS 11 nivel))
        (setq tamanot (cons 40 (* ESCALA 0.15)))
        (setq layert (cons 8 "PP"))                            
        (SETQ TEXTX (CONS 1 (RTOS (* (+ (ATOI YINI) CONT1) SEPRET) 2 0)))
        (ENTMAKE (LIST '(0 . "TEXT") '(100 . "AcDbEntity") layert '(370 . 25) '(100 . "AcDbText") XYZX tamanot TEXTX '(41 . 0.75) '(7 . "romans") '(72 . 0) xyzx2 '(73 . 2)))
        (setq valorx (cons 6  "bylayer"))
        (setq punretx (cons 10 (list (- X (* ESCALA 0.1239)) (* (+ (ATOI YINI) CONT1) SEPRET) 0)))
        (setq punretx2 (cons 11 (list (- X (* ESCALA 0.0489)) (* (+ (ATOI YINI) CONT1) SEPRET) 0)))
        (setq layersec (cons 8 "PP"))
        (ENTMAKE (LIST '(0 . "LINE") '(100 . "AcDbEntity") layersec '(370 . 25) valorx '(100 . "AcDbLine") PUNRETX PUNRETX2))
;        (COMMAND "INSERT" (STRCAT RUTA "BLOCKS\\LUTM2-2.dwg") XYZ5 ESCALA "" "")
;        (COMMAND "EXPLODE" (ENTLAST) "" "CHANGE" "P" "" "P" "LA" "PP" "")
;        (COMMAND "INSERT" (STRCAT RUTA "BLOCKS\\TEXTUTM2-2.dwg") XYZ3 ESCALA "" "")
;        (COMMAND "EXPLODE" (ENTLAST) "" "CHANGE" "P" "" "P" "LA" "PP" "" "CHANGE" "P" "" "" "" "" "" "" (RTOS (* (+ (ATOI YINI) CONT1) SEPRET) 2 0))
      )
    )
    (IF (= CONT1 0) 
      (PROGN
        (SETQ NIVEL (LIST (* (+ (ATOI XINI) CONT2) SEPRET) (+ Y (* ESCALA 16.71))))         ;0.279
        (SETQ XYZX (CONS 10 nivel))
        (SETQ XYZX2 (CONS 11 nivel))
        (setq tamanot (cons 40 (* ESCALA 0.15)))
        (setq layert (cons 8 "PP"))                            
        (SETQ TEXTX (CONS 1 (RTOS (* (+ (ATOI XINI) CONT2) SEPRET) 2 0)))
        (ENTMAKE (LIST '(0 . "TEXT") '(100 . "AcDbEntity") layert '(370 . 25) '(100 . "AcDbText") XYZX tamanot TEXTX '(41 . 0.75) '(7 . "romans") '(72 . 1) xyzx2 '(73 . 1)))
        (setq valorx (cons 6  "bylayer"))
        (setq punretx (cons 10 (list (* (+ (ATOI XINI) CONT2) SEPRET) (+ Y (* ESCALA 16.636)) 0)))
        (setq punretx2 (cons 11 (list (* (+ (ATOI XINI) CONT2) SEPRET) (+ Y (* ESCALA 16.71)) 0)))
        (setq layersec (cons 8 "PP"))
        (ENTMAKE (LIST '(0 . "LINE") '(100 . "AcDbEntity") layersec '(370 . 25) valorx '(100 . "AcDbLine") PUNRETX PUNRETX2))
        (SETQ NIVEL (LIST (* (+ (ATOI XINI) CONT2) SEPRET) (- Y (* ESCALA 0.35)) 0))         ;0.279
        (SETQ XYZX (CONS 10 nivel))
        (SETQ XYZX2 (CONS 11 nivel))
        (setq tamanot (cons 40 (* ESCALA 0.15)))
        (setq layert (cons 8 "PP"))                            
        (SETQ TEXTX (CONS 1 (RTOS (* (+ (ATOI XINI) CONT2) SEPRET) 2 0)))
        (ENTMAKE (LIST '(0 . "TEXT") '(100 . "AcDbEntity") layert '(370 . 25) '(100 . "AcDbText") XYZX tamanot TEXTX '(41 . 0.75) '(7 . "romans") '(72 . 1) xyzx2 '(73 . 1)))
        (setq valorx (cons 6  "bylayer"))
        (setq punretx (cons 10 (list (* (+ (ATOI XINI) CONT2) SEPRET) Y 0)))
        (setq punretx2 (cons 11 (list (* (+ (ATOI XINI) CONT2) SEPRET) (- Y (* ESCALA 0.075)) 0)))
        (setq layersec (cons 8 "PP"))
        (ENTMAKE (LIST '(0 . "LINE") '(100 . "AcDbEntity") layersec '(370 . 25) valorx '(100 . "AcDbLine") PUNRETX PUNRETX2))
;        (COMMAND "INSERT" (STRCAT RUTA "BLOCKS\\LUTM-2.dwg") XYZ4 ESCALA "" "")
;        (COMMAND "EXPLODE" (ENTLAST) "" "CHANGE" "P" "" "P" "LA" "PP" "")
;        (COMMAND "INSERT" (STRCAT RUTA "BLOCKS\\TEXTUTM-2.dwg") XYZ2 ESCALA "" "")
;        (COMMAND "EXPLODE" (ENTLAST) "" "CHANGE" "P" "" "P" "LA" "PP" "" "CHANGE" "P" "" "" "" "" "" "" (RTOS (* (+ (ATOI XINI) CONT2) SEPRET) 2 0))
      )
    )
    (SETQ CONT1 (1+ CONT1))
   )
   (SETQ CONT2 (1+ CONT2))
  )
  (SETQ NIVEL (LIST (- X (* ESCALA 0.9258)) (+ Y (* ESCALA 2.8755)) 0))         ;0.279
  (SETQ XYZX (CONS 10 nivel))
  (SETQ XYZX2 (CONS 11 nivel))
  (setq tamanot (cons 40 (* ESCALA 0.15)))
  (setq layert (cons 8 "PP"))                            
  (SETQ TEXTX (CONS 1 AREAclinica))
  (ENTMAKE (LIST '(0 . "TEXT") '(100 . "AcDbEntity") layert '(100 . "AcDbText") XYZX tamanot TEXTX '(41 . 0.75) '(7 . "romand") '(72 . 2) xyzx2 '(73 . 0)))
  (SETQ NIVEL (LIST (- X (* ESCALA 0.9258)) (+ Y (* ESCALA 0.4131)) 0))         ;0.279
  (SETQ XYZX (CONS 10 nivel))
  (SETQ XYZX2 (CONS 11 nivel))
  (SETQ TEXTX (CONS 1 AREAclinica))
  (ENTMAKE (LIST '(0 . "TEXT") '(100 . "AcDbEntity") layert '(100 . "AcDbText") XYZX tamanot TEXTX '(41 . 0.75) '(7 . "romand") '(72 . 2) xyzx2 '(73 . 0)))
  (SETQ NIVEL (LIST (+ X (* ESCALA 4.4847)) (+ Y (* ESCALA 3.6019)) 0))         ;0.279
  (SETQ XYZX (CONS 10 nivel))
  (SETQ XYZX2 (CONS 11 nivel))
  (setq tamanot (cons 40 (* ESCALA 0.15)))
  (setq layert (cons 8 "PP"))                            
  (SETQ TEXTX (CONS 1 (itoa zona)))
  (ENTMAKE (LIST '(0 . "TEXT") '(100 . "AcDbEntity") layert '(100 . "AcDbText") XYZX tamanot TEXTX '(7 . "XX") '(72 . 0) xyzx2 '(73 . 0)))
  (C:LIBRERIA "acota")
  (acotax poli (* 0.15 escala))
  (IF (= (STRCASE OPCION) "S")
    (IF (OR (= ESCALA 1) (= ESCALA 2) (= ESCALA 5))
      (PROGN
;        (if (= (getvar "acadver") "17.1s (LMS Tech)")
;          (COMMAND "INSERT" (STRCAT RUTA "BLOCKS\\" "SOLAR1.DWG") (STRCAT (RTOS CENTROIDEX1) "," (RTOS CENTROIDEY1)) ESCALA "")
          (COMMAND "INSERT" (STRCAT RUTA "BLOCKS\\" "SOLAR1.DWG") (STRCAT (RTOS CENTROIDEX1) "," (RTOS CENTROIDEY1)) ESCALA "" "" "")
;        )
      )
      (PROGN
;        (if (= (getvar "acadver") "17.1s (LMS Tech)")
;          (COMMAND "INSERT" (STRCAT RUTA "BLOCKS\\" "SOLAR2.DWG") (STRCAT (RTOS CENTROIDEX1) "," (RTOS CENTROIDEY1)) ESCALA "")
          (COMMAND "INSERT" (STRCAT RUTA "BLOCKS\\" "SOLAR2.DWG") (STRCAT (RTOS CENTROIDEX1) "," (RTOS CENTROIDEY1)) ESCALA "" "" "")
;        )
      )
    )
  )
  (COMMAND "VIEW" "R" "PROV")
  (SETVAR "OSMODE" OPCIONESOS)
)

(DEFUN C:CDING ()
  (command "undo" "m")
  (COMMAND "VIEW" "S" "PROV")
  (C:LIBRERIA "BUSCA VALOR DE ATRIBUTO")
  (C:LIBRERIA "SEPARA VALORES DE ESPACIOS DE UN TEXTO TO LISTA2")
  (SETQ OPCIONESOS (GETVAR "OSMODE"))
  (command "osnap" "none")
  (SETQ GPOTXT (SSGET ' ((0 .  "TEXT"))))
  (SETQ CONT (1- (SSLENGTH GPOTXT)))
  (SETQ CUADROBD NIL)
  (SETQ CONT2 1)
  (WHILE (> CONT 0)
    (SETQ CADENAX "")
    (REPEAT 8
      (SETQ ENT (SSNAME GPOTXT CONT))
      (SETQ CADENA (cdr (assoc 1 (ENTGET ENT))))
      (IF (= CADENAX "")
        (SETQ CADENAX CADENA)
        (SETQ CADENAX (STRCAT CADENAX " " CADENA))
      )
      (SETQ CONT (1- CONT))
    )
    (setq CONCATENADO (cons CONT2 CADENAX))        
    (setq CUADROBD (append CUADROBD (list CONCATENADO)))
    (SETQ CONT2 (1+ CONT2))
  )
  (SETQ CONT2 (1- CONT2))
  (SETQ EII (GETPOINT "\n ESQUINA INFERIOR IZQ. DE TABLA "))
  (SETQ X (CAR EII))
  (SETQ Y (CADR EII))
  (SETQ XFIN (+ X 355))
  (SETQ YFIN (+ Y (* CONT2 12.5)))
  (SETQ CONT 1)
  (REPEAT CONT2
    (SETQ XYZ (STRCAT (RTOS X 2 3) "," (RTOS (- YFIN (* CONT 12.5)) 2 3) ))
    (SETQ CADENAX (CDR (ASSOC CONT CUADROBD)))
    (SETQ DATOSL1 (SEPARA_VAL_SPC CADENAX))
;    (if (= (getvar "acadver") "17.1s (LMS Tech)")
;      (COMMAND "INSERt" (STRCAT RUTA "BLOCKS\\lxing.dwg") xyz "")
      (COMMAND "INSERt" (STRCAT RUTA "BLOCKS\\lxing.dwg") xyz "" "" "")
;    )
    (COMMAND "EXPLODE" (ENTLASt) "")
;    (if (= (getvar "acadver") "17.1s (LMS Tech)")
;      (COMMAND "INSERt" (STRCAT RUTA "BLOCKS\\CDTXT2.dwg") xyz "")
      (COMMAND "INSERt" (STRCAT RUTA "BLOCKS\\CDTXT2.dwg") xyz "" "" "")
;    )
    (COMMAND "EXPLODE" (ENTLASt) "")
    (SETQ GPOTXTP (SSGET "P"))
    (SETQ CONT3 0)
    (REPEAT 8
      (IF (= CONT3 0) (SETQ ATRIBUTOC (CDR (ASSOC 2 DATOSL1))))
      (IF (= CONT3 1) (SETQ ATRIBUTOC (CDR (ASSOC 1 DATOSL1))))
      (IF (> CONT3 1) (SETQ ATRIBUTOC (CDR (ASSOC (1+ CONT3) DATOSL1))))
      (if (or (= 2 cont3) (= 3 cont3) (= 4 cont3)) (progn (setq atributoc (qcomas atributoc)) (setq atributoc (rtos (atof atributoc) 2 3))))
      (IF (= CONT3 3) (SETQ PX ATRIBUTOC))
      (IF (= CONT3 4) (SETQ PY ATRIBUTOC))
      (SETQ ENTX (SSNAME GPOTXTP CONT3))
      (setq nte (STRCAT atributoc))
      (entmod (subst (cons 1 nte) (assoc 1 (entget entx)) (entget entx)))
      ;(COMMAND "CHANGE" ENTX "" "" "" "" "" "" ATRIBUTOC)
      (SETQ CONT3 (1+ CONT3))
    )

        (SETQ PXYZ (LIST (ATOF PX) (ATOF PY) 0))
        (COMMAND "ZOOM" "C" PXYZ "1")
        (setq gnupo (ssget "C" (suma PXYZ 0.01 0.01) (suma Pxyz -0.01 -0.01)))
        (setq conta 0)
        (setq enco2 0)
        (while (/= conta (sslength gnupo))
          (setq nnupo (ssname gnupo conta))
          (SETQ PVX (cdr (assoc 10 (entget nnupo))))
          (SETQ XV (CAR PVX))
          (SETQ YV (CADR PVX))
          (SETQ X1 (CAR Pxyz))
          (SETQ Y1 (CADR Pxyz))
          (SETQ NOMBREP (cdr (assoc 2 (entget nnupo))))
          (if (OR (= "PUNTO" NOMBREP) (= "pun2" NOMBREP) (= "PUN2" NOMBREP) (= "punto" NOMBREP))
            (IF (AND (= (RTOS XV 2 3) (RTOS X1 2 3)) (= (RTOS YV 2 3) (RTOS Y1 2 3)))
              (progn
                (setq enco2 1)
                (setq conta (- (sslength gnupo) 1))
              )
            )    ;if
          )   ;IF
          (setq conta (+ conta 1))
        )    ;WHILE
        (if (= enco2 1)
          (progn
            (setq numpun (busatr NNUPO "PUNTO"))
            (setq espu (cdr (assoc 41 (entget nnupo))))
          )
        )
        (COMMAND "ZOOM" "P")
        (IF (= CONT 1)
          (PROGN
            (SETQ ENTX2 (SSNAME GPOTXTP 1))
            (SETQ NUMEROINICIAL NUMPUN)
            (SETQ NUMEROINICIAL2 NUMPUN)
          )
        )
        (IF (> CONT 1)
          (PROGN
            (SETQ ENTX (SSNAME GPOTXTP 1))
            (setq nte (STRCAT NUMEROINICIAL " - " NUMPUN))
            (SETQ NUMEROINICIAL NUMPUN)
            (entmod (subst (cons 1 nte) (assoc 1 (entget entx2)) (entget entx2)))
            (SETQ ENTX2 ENTX)
          )
        )

    (SETQ CONT (1+ CONT))
  )  
  (setq nte (STRCAT NUMEROINICIAL " - " NUMEROINICIAL2))
  (entmod (subst (cons 1 nte) (assoc 1 (entget entx2)) (entget entx2)))

  (command "line" eii (strcat (RTOS X 2 4) "," (RTOS yfin 2 4) ) "")
  (command "copy" (entlast) "" "m" eii (strcat (RTOS (+ X 43.75) 2 4) "," (RTOS y 2 4)) (strcat (RTOS (+ X 93.75) 2 4) "," (RTOS y 2 4)) (strcat (RTOS (+ X 131.25) 2 4) "," (RTOS y 2 4)) (strcat (RTOS (+ X 172.5) 2 4) "," (RTOS y 2 4)) (strcat (RTOS (+ X 215) 2 4) "," (RTOS y 2 4)) (strcat (RTOS (+ X 265) 2 4) "," (RTOS y 2 4)) (strcat (RTOS (+ X 315) 2 4) "," (RTOS y 2 4)) (strcat (RTOS (+ X 355) 2 4) "," (RTOS y 2 4)) "")
;  (if (= (getvar "acadver") "17.1s (LMS Tech)")
;    (COMMAND "INSERt" (STRCAT RUTA "BLOCKS\\ENCABEZADO.dwg") (strcat (RTOS X 2 4) "," (RTOS yfin 2 4)) "")
    (COMMAND "INSERt" (STRCAT RUTA "BLOCKS\\ENCABEZADO.dwg") (strcat (RTOS X 2 4) "," (RTOS yfin 2 4)) "" "" "")
;  )
  (COMMAND "EXPLODE" (ENTLASt) "")
  (COMMAND "VIEW" "R" "PROV")
  (SETVAR "OSMODE" OPCIONESOS)
)

(DEFUN C:CDING2 ()
  (command "undo" "m")
  (COMMAND "VIEW" "S" "PROV")
  (C:LIBRERIA "BUSCA VALOR DE ATRIBUTO")
  (C:LIBRERIA "SEPARA VALORES DE ESPACIOS DE UN TEXTO TO LISTA2")
  (COMMAND "DIMZIN" 1)
  (COMMAND "LUNITS" 2)
  (COMMAND "LUPREC" 3)
  (COMMAND "AUNITS" 4)
  (COMMAND "AUPREC" 4)
  (COMMAND "ANGDIR" 0)
  (COMMAND "ANGBASE" 0.0)
  (SETQ OPCIONESOS (GETVAR "OSMODE"))
  (command "osnap" "none")
  (setq cuadro (car (entsel "\n Selecciona el cuadro de construccion: ")))
  (command "explode" (entlast) "")
  (setq gpotxt (ssget "p" '((0 . "TEXT"))))
  (SETQ CONT 0)
  (SETQ CUADROBD NIL)
  (SETQ CONT2 1)
  (WHILE (< CONT (SSLENGTH GPOTXT))
    (SETQ CADENAX "")
    (REPEAT 8
      (SETQ ENT (SSNAME GPOTXT CONT))
      (SETQ CADENA (cdr (assoc 1 (ENTGET ENT))))
      (IF (= CADENAX "")
        (SETQ CADENAX CADENA)
        (SETQ CADENAX (STRCAT CADENAX " " CADENA))
      )
      (SETQ CONT (1+ CONT))
    )
    (setq CONCATENADO (cons CONT2 CADENAX))        
    (setq CUADROBD (append CUADROBD (list CONCATENADO)))
    (SETQ CONT2 (1+ CONT2))
  )

  (SETQ CADENAX (CDR (ASSOC 1 CUADROBD)))
  (SETQ DATOSL1 (SEPARA_VAL_SPC CADENAX))
  (SETQ PX (CDR (ASSOC 7 DATOSL1)))
  (SETQ PY (CDR (ASSOC 8 DATOSL1)))
  (SETQ PXYZ (LIST (ATOF PX) (ATOF PY) 0))
  (COMMAND "ZOOM" "C" PXYZ "1")
  (setq gnupo (ssget "C" (suma PXYZ 0.01 0.01) (suma Pxyz -0.01 -0.01) '((0 . "LWPOLYLINE"))))
;  (COMMAND "ZOOM" "P")
  (SETQ CONTF 2)
  (while (AND (/= 1 (sslength gnupo)) (/= NIL gnupo))
    (SETQ CADENAX (CDR (ASSOC CONTF CUADROBD)))
    (SETQ DATOSL1 (SEPARA_VAL_SPC CADENAX))
    (SETQ PX (CDR (ASSOC 7 DATOSL1)))
    (SETQ PY (CDR (ASSOC 8 DATOSL1)))
    (SETQ PXYZ (LIST (ATOF PX) (ATOF PY) 0))
    (COMMAND "ZOOM" "C" PXYZ "1")
    (setq gnupo (ssget "C" (suma PXYZ 0.01 0.01) (suma Pxyz -0.01 -0.01) '((0 . "LWPOLYLINE"))))
;    (COMMAND "ZOOM" "P")
    (SETQ CONTF (1+ CONTF))
  );WHILE
  (SETQ BDLIN NIL)
  (SETQ LIN (SSNAME GNUPO 0))

    (SETQ J 0)
    (SETQ VER1 "")
    (WHILE VER1
       (setq J (1+ J))
       (SETQ VER1 (verticeSURF lin J))
       (IF (/= VER1 NIL)
        (PROGN
         (COMMAND "ZOOM" "C" (suma VER1 0.01 0.01) "1")
         (setq gnupo (ssget "C" (suma VER1 0.01 0.01) (suma VER1 -0.01 -0.01)))
         (setq conta 0)
         (setq enco 0)
         (while (/= conta (sslength gnupo))
           (setq nnupo (ssname gnupo conta))
           (SETQ PV (cdr (assoc 10 (entget nnupo))))
           (SETQ XV (CAR PV))
           (SETQ YV (CADR PV))
           (SETQ X1 (CAR VER1))
           (SETQ Y1 (CADR VER1))
           (if (OR (= "PUN2" (cdr (assoc 2 (entget nnupo)))) (= "PUNTO" (cdr (assoc 2 (entget nnupo)))))
             (IF (AND (= (RTOS XV 2 2) (RTOS X1 2 2)) (= (RTOS YV 2 2) (RTOS Y1 2 2)))
               (progn
                 (setq enco 1)
                 (setq conta (- (sslength gnupo) 1))
               )
             )
           );IF
           (setq conta (+ conta 1))
         );WHILE
         (if (= enco 1)
           (progn
             (setq CODES (BUSATR nnupo "CODE"))
             (setq ELEVS (BUSATR nnupo "ELEV"))
             (setq PUNTOS (BUSATR nnupo "PUNTO"))
;             (setq numpun (cdr (assoc 1 (entget atr1))))
;             (setq espu (cdr (assoc 41 (entget nnupo))))
           );PROGN
           (progn
            (ALERT "NO SE ENCONTRO BLOCK EN UN VERTICE")
            (COMMAND "VIEW" "S" "MSA")
            (COMMAND "ZOOM" "C" VER1 "10")
            (COMMAND "CIRCLE" VER1 ".1")
            (SETQ PROVE (ENTLAST))
            (setQ OPT2 (GETSTRING "DESEAS /I-nsertar/S-eleccionar/ EL BLOCK (I/S) <I> :"))
            (IF (= "CIRCLE" (cdr (assoc 0 (ENTGET PROVE))))
              (COMMAND "ERASE" PROVE "")
            );IF
            (COMMAND "VIEW" "R" "MSA")
            (IF (= OPT2 "")
               (SETQ OPT2 "I") 
            );IF
            (IF (= (STRCASE OPT2) "I")
              (PROGN
               (setQ OPT3 (GETREAL (STRCAT "NUMERO DE PUNTO A INSERTAR <"(RTOS (1+ ARRANQUE) 2 0) "> :")))
               (IF (/= OPT3 NIL)
                  (SETQ ARRANQUE (1- OPT3)) 
               );IF                      
;               (if (= (getvar "acadver") "17.1s (LMS Tech)")
;                 (command "INSERT" (STRCAT RUTA "BLOCKS\\PUNTO") VER1 "" "" "" (rtos (+ arranque 1) 2 0)  "AUTOMATICO" "")
                 (command "INSERT" (STRCAT RUTA "BLOCKS\\PUNTO") VER1 "" "" "" (rtos (+ arranque 1) 2 0)  "AUTOMATICO" "")
;               )
               (command "CHANGE" (entlast) "" "P" "LA" "AUTOMATICO" "")
               (setq arranque (+ arranque 1))
               (setq numpun (rtos arranque 2 0))
              );PROGN
              (PROGN 
               (setq PROVE (car (entsel "Selecciona el bloque a MOVER: ")))
               (command "MOVE" PROVE "" (cdr (assoc 10 (entget PROVE))) VER1)
              );PROGN 
            );IF
            (SETQ PUNTOS (rtos arranque 2 0))
            (SETQ CODES "AUTOMATICO")
            (SETQ ELEVS "0")
           );PROGN
         );IF
 ;         );WHILE
         (IF (= ELEVS NIL) (SETQ ELEVS "1"))
         (IF (= CODES NIL) (SETQ CODES "X"))
         (IF (= PUNTOS NIL) (SETQ PUNTOS "N"))
         (IF (> J 1)
           (IF (/= VER1 NIL)
             (PROGN
               (SETQ CADENAX (strcat NPTO "-" PUNTOS " " (RTOS (DISTANCE (LIST (ATOF PRIMX) (ATOF PRIMY) 0) (LIST (car ver1) (car (cdr ver1)) 0)) 2 3) " " PRIMX " " PRIMY))
               (setq CONCATENADO (cons (1- J) CADENAX))
               (setq BDLIN (append BDLIN (list CONCATENADO)))
               (SETQ PRIMX (rtos (car ver1) 2 3))
               (SETQ PRIMY (rtos (car (cdr ver1)) 2 3))
               (SETQ NPTO PUNTOS)
             );PROGN
           );IF
           (PROGN
             (SETQ XINICIO (rtos (car ver1) 2 3))
             (SETQ YINICIO (rtos (car (cdr ver1)) 2 3))
             (SETQ NPTOINI PUNTOS)
             (SETQ PRIMX (rtos (car ver1) 2 3))
             (SETQ PRIMY (rtos (car (cdr ver1)) 2 3))
             (SETQ NPTO PUNTOS)
           );PROGN
         )
        );PROGN
      );IF
    );WHILE
    (SETQ CADENAX (strcat PUNTOS "-" NPTOINI " " (RTOS (DISTANCE (LIST (ATOF XINICIO) (ATOF YINICIO)) (LIST (ATOF PRIMX) (ATOF PRIMY))) 2 3) " " PRIMX " " PRIMY))
    (setq CONCATENADO (cons (1- J) CADENAX))
    (setq BDLIN (append BDLIN (list CONCATENADO)))

  (SETQ CONT2 (1- CONT2))
  (SETQ EII (GETPOINT "\n ESQUINA INFERIOR IZQ. DE TABLA "))
  (SETQ X (CAR EII))
  (SETQ Y (CADR EII))
  (SETQ XFIN (+ X 355))
  (SETQ YFIN (+ Y (* CONT2 12.5)))
  (SETQ CONT 1)
  (REPEAT CONT2
    (SETQ XYZ (STRCAT (RTOS X 2 3) "," (RTOS (- YFIN (* CONT 12.5)) 2 3) ))
    (SETQ CADENAX (CDR (ASSOC CONT CUADROBD)))
    (SETQ DATOSL1 (SEPARA_VAL_SPC CADENAX))
    (SETQ CADENAX2 (CDR (ASSOC CONT BDLIN)))
    (SETQ DATOSL2 (SEPARA_VAL_SPC CADENAX2))
;    (if (= (getvar "acadver") "17.1s (LMS Tech)")
;      (COMMAND "INSERt" (STRCAT RUTA "BLOCKS\\lxing.dwg") xyz "")
      (COMMAND "INSERt" (STRCAT RUTA "BLOCKS\\lxing.dwg") xyz "" "" "")
;    )
    (COMMAND "EXPLODE" (ENTLASt) "")
;    (if (= (getvar "acadver") "17.1s (LMS Tech)")
;      (COMMAND "INSERt" (STRCAT RUTA "BLOCKS\\CDTXT2.dwg") xyz "")
      (COMMAND "INSERt" (STRCAT RUTA "BLOCKS\\CDTXT2.dwg") xyz "" "" "")
;    )
    (COMMAND "EXPLODE" (ENTLASt) "")
    (SETQ GPOTXTP (SSGET "P"))
    (SETQ CONT3 0)
    (REPEAT 8
      (IF (= CONT3 0) (SETQ ATRIBUTOC (STRCAT (CDR (ASSOC 2 DATOSL1)) (CDR (ASSOC 3 DATOSL1)) (CDR (ASSOC 4 DATOSL1)))))
      (IF (= CONT3 1) (SETQ ATRIBUTOC (ceros (CDR (ASSOC 5 DATOSL1)))))
      (IF (= CONT3 2) (SETQ ATRIBUTOC (CDR (ASSOC 2 DATOSL2))))
      (IF (= CONT3 3) (SETQ ATRIBUTOC (CDR (ASSOC 3 DATOSL2))))
      (IF (= CONT3 4) (SETQ ATRIBUTOC (CDR (ASSOC 4 DATOSL2))))
;      (IF (> CONT3 1) (SETQ ATRIBUTOC (CDR (ASSOC (1+ CONT3) DATOSL1))))
;      (if (or (= 2 cont3) (= 3 cont3) (= 4 cont3)) (progn (setq atributoc (qcomas atributoc)) (setq atributoc (rtos (atof atributoc) 2 3))))
      (IF (= CONT3 5) (SETQ ATRIBUTOC (ceros (CDR (ASSOC 9 DATOSL1)))))
      (IF (= CONT3 6) (SETQ ATRIBUTOC (ceros (CDR (ASSOC 10 DATOSL1)))))
      (IF (= CONT3 7) (SETQ ATRIBUTOC (CDR (ASSOC 1 DATOSL1))))
      (SETQ ENTX (SSNAME GPOTXTP CONT3))
      (setq nte (STRCAT atributoc))
      (entmod (subst (cons 1 nte) (assoc 1 (entget entx)) (entget entx)))
      ;(COMMAND "CHANGE" ENTX "" "" "" "" "" "" ATRIBUTOC)
      (SETQ CONT3 (1+ CONT3))
    )

;        (SETQ PXYZ (LIST (ATOF PX) (ATOF PY) 0))
;        (COMMAND "ZOOM" "C" PXYZ "1")
;        (setq gnupo (ssget "C" (suma PXYZ 0.01 0.01) (suma Pxyz -0.01 -0.01) '((0 . "LWPOLYLINE"))))
;        (setq conta 0)
;        (setq enco2 0)
;        (while (/= conta (sslength gnupo))
;          (setq nnupo (ssname gnupo conta))
;          (SETQ PVX (cdr (assoc 10 (entget nnupo))))
;          (SETQ XV (CAR PVX))
;          (SETQ YV (CADR PVX))
;          (SETQ X1 (CAR Pxyz))
;          (SETQ Y1 (CADR Pxyz))
;          (SETQ NOMBREP (cdr (assoc 2 (entget nnupo))))
;          (if (OR (= "PUNTO" NOMBREP) (= "pun2" NOMBREP) (= "PUN2" NOMBREP) (= "punto" NOMBREP))
;            (IF (AND (= (RTOS XV 2 3) (RTOS X1 2 3)) (= (RTOS YV 2 3) (RTOS Y1 2 3)))
;              (progn
;                (setq enco2 1)
;                (setq conta (- (sslength gnupo) 1))
;              )
;            )    ;if
;          )   ;IF
;          (setq conta (+ conta 1))
;        )    ;WHILE
;        (if (= enco2 1);
;          (progn
;            (setq numpun (busatr NNUPO "PUNTO"))
;            (setq espu (cdr (assoc 41 (entget nnupo))))
;          )
;        )
;        (COMMAND "ZOOM" "P")
;        (IF (= CONT 1)
;          (PROGN
;            (SETQ ENTX2 (SSNAME GPOTXTP 1))
;            (SETQ NUMEROINICIAL NUMPUN)
;            (SETQ NUMEROINICIAL2 NUMPUN)
;          )
;        )
;        (IF (> CONT 1)
;          (PROGN
;            (SETQ ENTX (SSNAME GPOTXTP 1))
;            (setq nte (STRCAT NUMEROINICIAL " - " NUMPUN))
;            (SETQ NUMEROINICIAL NUMPUN)
;            (entmod (subst (cons 1 nte) (assoc 1 (entget entx2)) (entget entx2)))
;            (SETQ ENTX2 ENTX)
;          )
;        )
;
    (SETQ CONT (1+ CONT))
  )  
;  (setq nte (STRCAT NUMEROINICIAL " - " NUMEROINICIAL2))
;  (entmod (subst (cons 1 nte) (assoc 1 (entget entx2)) (entget entx2)))

  (command "line" eii (strcat (RTOS X 2 4) "," (RTOS yfin 2 4) ) "")
  (command "copy" (entlast) "" "m" eii (strcat (RTOS (+ X 42.443) 2 4) "," (RTOS y 2 4)) (strcat (RTOS (+ X 90.950) 2 4) "," (RTOS y 2 4)) (strcat (RTOS (+ X 127.33) 2 4) "," (RTOS y 2 4)) (strcat (RTOS (+ X 173.174) 2 4) "," (RTOS y 2 4)) (strcat (RTOS (+ X 219.827) 2 4) "," (RTOS y 2 4)) (strcat (RTOS (+ X 268.334) 2 4) "," (RTOS y 2 4)) (strcat (RTOS (+ X 316.84) 2 4) "," (RTOS y 2 4)) (strcat (RTOS (+ X 355.646) 2 4) "," (RTOS y 2 4)) "")
;  (if (= (getvar "acadver") "17.1s (LMS Tech)")
;    (COMMAND "INSERt" (STRCAT RUTA "BLOCKS\\ENCABEZADO.dwg") (strcat (RTOS X 2 4) "," (RTOS yfin 2 4)) "")
    (COMMAND "INSERt" (STRCAT RUTA "BLOCKS\\ENCABEZADO.dwg") (strcat (RTOS X 2 4) "," (RTOS yfin 2 4)) "" "" "")
;  )
  (COMMAND "EXPLODE" (ENTLASt) "")
  (COMMAND "VIEW" "R" "PROV")
  (SETVAR "OSMODE" OPCIONESOS)
)

(DEFUN C:CDING3 ()
  (command "undo" "m")
  (COMMAND "VIEW" "S" "PROV")
  (C:LIBRERIA "BUSCA VALOR DE ATRIBUTO")
  (C:LIBRERIA "SEPARA VALORES DE ESPACIOS DE UN TEXTO TO LISTA2")
  (COMMAND "DIMZIN" 1)
  (COMMAND "LUNITS" 2)
  (COMMAND "LUPREC" 3)
  (COMMAND "AUNITS" 4)
  (COMMAND "AUPREC" 4)
  (COMMAND "ANGDIR" 0)
  (COMMAND "ANGBASE" 0.0)
  (SETQ OPCIONESOS (GETVAR "OSMODE"))
  (command "osnap" "none")
  (setq cuadro (car (entsel "\n Selecciona el cuadro de construccion: ")))
  (command "explode" (entlast) "")
  (setq gpotxt (ssget "p" '((0 . "TEXT"))))
  (SETQ CONT 0)
  (SETQ CUADROBD NIL)
  (SETQ CONT2 1)
  (WHILE (< CONT (SSLENGTH GPOTXT))
    (SETQ CADENAX "")
    (REPEAT 8
      (SETQ ENT (SSNAME GPOTXT CONT))
      (SETQ CADENA (cdr (assoc 1 (ENTGET ENT))))
      (IF (= CADENAX "")
        (SETQ CADENAX CADENA)
        (SETQ CADENAX (STRCAT CADENAX " " CADENA))
      )
      (SETQ CONT (1+ CONT))
    )
    (setq CONCATENADO (cons CONT2 CADENAX))        
    (setq CUADROBD (append CUADROBD (list CONCATENADO)))
    (SETQ CONT2 (1+ CONT2))
  )

  (SETQ CADENAX (CDR (ASSOC 1 CUADROBD)))
  (SETQ DATOSL1 (SEPARA_VAL_SPC CADENAX))
  (SETQ PX (CDR (ASSOC 6 DATOSL1)))
  (SETQ PY (CDR (ASSOC 7 DATOSL1)))
  (SETQ PXYZ (LIST (ATOF PX) (ATOF PY) 0))
  (COMMAND "ZOOM" "C" PXYZ "1")
  (setq gnupo (ssget "C" (suma PXYZ 0.01 0.01) (suma Pxyz -0.01 -0.01) '((0 . "LWPOLYLINE"))))
;  (COMMAND "ZOOM" "P")
  (SETQ CONTF 2)
  (while (AND (/= 1 (sslength gnupo)) (/= NIL gnupo))
    (SETQ CADENAX (CDR (ASSOC CONTF CUADROBD)))
    (SETQ DATOSL1 (SEPARA_VAL_SPC CADENAX))
    (SETQ PX (CDR (ASSOC 6 DATOSL1)))
    (SETQ PY (CDR (ASSOC 7 DATOSL1)))
    (SETQ PXYZ (LIST (ATOF PX) (ATOF PY) 0))
    (COMMAND "ZOOM" "C" PXYZ "1")
    (setq gnupo (ssget "C" (suma PXYZ 0.01 0.01) (suma Pxyz -0.01 -0.01) '((0 . "LWPOLYLINE"))))
;    (COMMAND "ZOOM" "P")
    (SETQ CONTF (1+ CONTF))
  );WHILE
  (SETQ BDLIN NIL)
  (SETQ LIN (SSNAME GNUPO 0))

    (SETQ J 0)
    (SETQ VER1 "")
    (WHILE VER1
       (setq J (1+ J))
       (SETQ VER1 (verticeSURF lin J))
       (IF (/= VER1 NIL)
        (PROGN
         (COMMAND "ZOOM" "C" (suma VER1 0.01 0.01) "1")
         (setq gnupo (ssget "C" (suma VER1 0.01 0.01) (suma VER1 -0.01 -0.01)))
         (setq conta 0)
         (setq enco 0)
         (while (/= conta (sslength gnupo))
           (setq nnupo (ssname gnupo conta))
           (SETQ PV (cdr (assoc 10 (entget nnupo))))
           (SETQ XV (CAR PV))
           (SETQ YV (CADR PV))
           (SETQ X1 (CAR VER1))
           (SETQ Y1 (CADR VER1))
           (if (OR (= "PUN2" (cdr (assoc 2 (entget nnupo)))) (= "PUNTO" (cdr (assoc 2 (entget nnupo)))))
             (IF (AND (= (RTOS XV 2 2) (RTOS X1 2 2)) (= (RTOS YV 2 2) (RTOS Y1 2 2)))
               (progn
                 (setq enco 1)
                 (setq conta (- (sslength gnupo) 1))
               )
             )
           );IF
           (setq conta (+ conta 1))
         );WHILE
         (if (= enco 1)
           (progn
             (setq CODES (BUSATR nnupo "CODE"))
             (setq ELEVS (BUSATR nnupo "ELEV"))
             (setq PUNTOS (BUSATR nnupo "PUNTO"))
;             (setq numpun (cdr (assoc 1 (entget atr1))))
;             (setq espu (cdr (assoc 41 (entget nnupo))))
           );PROGN
           (progn
            (ALERT "NO SE ENCONTRO BLOCK EN UN VERTICE")
            (COMMAND "VIEW" "S" "MSA")
            (COMMAND "ZOOM" "C" VER1 "10")
            (COMMAND "CIRCLE" VER1 ".1")
            (SETQ PROVE (ENTLAST))
            (setQ OPT2 (GETSTRING "DESEAS /I-nsertar/S-eleccionar/ EL BLOCK (I/S) <I> :"))
            (IF (= "CIRCLE" (cdr (assoc 0 (ENTGET PROVE))))
              (COMMAND "ERASE" PROVE "")
            );IF
            (COMMAND "VIEW" "R" "MSA")
            (IF (= OPT2 "")
               (SETQ OPT2 "I") 
            );IF
            (IF (= (STRCASE OPT2) "I")
              (PROGN
               (setQ OPT3 (GETREAL (STRCAT "NUMERO DE PUNTO A INSERTAR <"(RTOS (1+ ARRANQUE) 2 0) "> :")))
               (IF (/= OPT3 NIL)
                  (SETQ ARRANQUE (1- OPT3)) 
               );IF                      
;               (if (= (getvar "acadver") "17.1s (LMS Tech)")
;                 (command "INSERT" (STRCAT RUTA "BLOCKS\\PUNTO") VER1 "" "" "" (rtos (+ arranque 1) 2 0)  "AUTOMATICO" "" "")
                 (command "INSERT" (STRCAT RUTA "BLOCKS\\PUNTO") VER1 "" "" "" (rtos (+ arranque 1) 2 0)  "AUTOMATICO" "" "")
;               )
;               (if (= (getvar "acadver") "17.1s (LMS Tech)")
;                 (command "INSERT" (STRCAT RUTA "BLOCKS\\PUNTO") VER1 "" "" "" (rtos (+ arranque 1) 2 0)  "AUTOMATICO" "" "")
                 (command "INSERT" (STRCAT RUTA "BLOCKS\\PUNTO") VER1 "" "" "" (rtos (+ arranque 1) 2 0)  "AUTOMATICO" "" "")
;               )
               (command "CHANGE" (entlast) "" "P" "LA" "AUTOMATICO" "")
               (setq arranque (+ arranque 1))
               (setq numpun (rtos arranque 2 0))
              );PROGN
              (PROGN 
               (setq PROVE (car (entsel "Selecciona el bloque a MOVER: ")))
               (command "MOVE" PROVE "" (cdr (assoc 10 (entget PROVE))) VER1)
              );PROGN 
            );IF
            (SETQ PUNTOS (rtos arranque 2 0))
            (SETQ CODES "AUTOMATICO")
            (SETQ ELEVS "0")
           );PROGN
         );IF
 ;         );WHILE
         (IF (= ELEVS NIL) (SETQ ELEVS "1"))
         (IF (= CODES NIL) (SETQ CODES "X"))
         (IF (= PUNTOS NIL) (SETQ PUNTOS "N"))
         (IF (> J 1)
           (IF (/= VER1 NIL)
             (PROGN
               (SETQ CADENAX (strcat NPTO "-" PUNTOS " " (RTOS (DISTANCE (LIST (ATOF PRIMX) (ATOF PRIMY) 0) (LIST (car ver1) (car (cdr ver1)) 0)) 2 3) " " PRIMX " " PRIMY))
               (setq CONCATENADO (cons (1- J) CADENAX))
               (setq BDLIN (append BDLIN (list CONCATENADO)))
               (SETQ PRIMX (rtos (car ver1) 2 3))
               (SETQ PRIMY (rtos (car (cdr ver1)) 2 3))
               (SETQ NPTO PUNTOS)
             );PROGN
           );IF
           (PROGN
             (SETQ XINICIO (rtos (car ver1) 2 3))
             (SETQ YINICIO (rtos (car (cdr ver1)) 2 3))
             (SETQ NPTOINI PUNTOS)
             (SETQ PRIMX (rtos (car ver1) 2 3))
             (SETQ PRIMY (rtos (car (cdr ver1)) 2 3))
             (SETQ NPTO PUNTOS)
           );PROGN
         )
        );PROGN
      );IF
    );WHILE
    (SETQ CADENAX (strcat PUNTOS "-" NPTOINI " " (RTOS (DISTANCE (LIST (ATOF XINICIO) (ATOF YINICIO)) (LIST (ATOF PRIMX) (ATOF PRIMY))) 2 3) " " PRIMX " " PRIMY))
    (setq CONCATENADO (cons (1- J) CADENAX))
    (setq BDLIN (append BDLIN (list CONCATENADO)))

  (SETQ CONT2 (1- CONT2))
  (SETQ EII (GETPOINT "\n ESQUINA INFERIOR IZQ. DE TABLA "))
  (SETQ X (CAR EII))
  (SETQ Y (CADR EII))
  (SETQ XFIN (+ X 355))
  (SETQ YFIN (+ Y (* CONT2 12.5)))
  (SETQ CONT 1)
  (REPEAT CONT2
    (SETQ XYZ (STRCAT (RTOS X 2 3) "," (RTOS (- YFIN (* CONT 12.5)) 2 3) ))
    (SETQ CADENAX (CDR (ASSOC CONT CUADROBD)))
    (SETQ DATOSL1 (SEPARA_VAL_SPC CADENAX))
    (SETQ CADENAX2 (CDR (ASSOC CONT BDLIN)))
    (SETQ DATOSL2 (SEPARA_VAL_SPC CADENAX2))
;    (if (= (getvar "acadver") "17.1s (LMS Tech)")
;      (COMMAND "INSERt" (STRCAT RUTA "BLOCKS\\lxing.dwg") xyz "")
      (COMMAND "INSERt" (STRCAT RUTA "BLOCKS\\lxing.dwg") xyz "" "" "")
;    )
    (COMMAND "EXPLODE" (ENTLASt) "")
;    (if (= (getvar "acadver") "17.1s (LMS Tech)")
;      (COMMAND "INSERt" (STRCAT RUTA "BLOCKS\\CDTXT2.dwg") xyz "")
      (COMMAND "INSERt" (STRCAT RUTA "BLOCKS\\CDTXT2.dwg") xyz "" "" "")
;    )
    (COMMAND "EXPLODE" (ENTLASt) "")
    (SETQ GPOTXTP (SSGET "P"))
    (SETQ CONT3 0)
    (REPEAT 8
      (IF (= CONT3 0) (SETQ ATRIBUTOC (STRCAT (CDR (ASSOC 1 DATOSL1)) (CDR (ASSOC 2 DATOSL1)) (CDR (ASSOC 3 DATOSL1)))))
      (IF (= CONT3 1) (SETQ ATRIBUTOC (ceros (CDR (ASSOC 4 DATOSL1)))))
      (IF (= CONT3 2) (SETQ ATRIBUTOC (CDR (ASSOC 2 DATOSL2))))
      (IF (= CONT3 3) (SETQ ATRIBUTOC (CDR (ASSOC 3 DATOSL2))))
      (IF (= CONT3 4) (SETQ ATRIBUTOC (CDR (ASSOC 4 DATOSL2))))
;      (IF (> CONT3 1) (SETQ ATRIBUTOC (CDR (ASSOC (1+ CONT3) DATOSL1))))
;      (if (or (= 2 cont3) (= 3 cont3) (= 4 cont3)) (progn (setq atributoc (qcomas atributoc)) (setq atributoc (rtos (atof atributoc) 2 3))))
      (IF (= CONT3 5) (SETQ ATRIBUTOC (ceros (CDR (ASSOC 8 DATOSL1)))))
      (IF (= CONT3 6) (SETQ ATRIBUTOC (ceros (CDR (ASSOC 9 DATOSL1)))))
      (IF (= CONT3 7) (SETQ ATRIBUTOC (CDR (ASSOC 10 DATOSL1))))
      (SETQ ENTX (SSNAME GPOTXTP CONT3))
      (setq nte (STRCAT atributoc))
      (entmod (subst (cons 1 nte) (assoc 1 (entget entx)) (entget entx)))
      ;(COMMAND "CHANGE" ENTX "" "" "" "" "" "" ATRIBUTOC)
      (SETQ CONT3 (1+ CONT3))
    )

;        (SETQ PXYZ (LIST (ATOF PX) (ATOF PY) 0))
;        (COMMAND "ZOOM" "C" PXYZ "1")
;        (setq gnupo (ssget "C" (suma PXYZ 0.01 0.01) (suma Pxyz -0.01 -0.01) '((0 . "LWPOLYLINE"))))
;        (setq conta 0)
;        (setq enco2 0)
;        (while (/= conta (sslength gnupo))
;          (setq nnupo (ssname gnupo conta))
;          (SETQ PVX (cdr (assoc 10 (entget nnupo))))
;          (SETQ XV (CAR PVX))
;          (SETQ YV (CADR PVX))
;          (SETQ X1 (CAR Pxyz))
;          (SETQ Y1 (CADR Pxyz))
;          (SETQ NOMBREP (cdr (assoc 2 (entget nnupo))))
;          (if (OR (= "PUNTO" NOMBREP) (= "pun2" NOMBREP) (= "PUN2" NOMBREP) (= "punto" NOMBREP))
;            (IF (AND (= (RTOS XV 2 3) (RTOS X1 2 3)) (= (RTOS YV 2 3) (RTOS Y1 2 3)))
;              (progn
;                (setq enco2 1)
;                (setq conta (- (sslength gnupo) 1))
;              )
;            )    ;if
;          )   ;IF
;          (setq conta (+ conta 1))
;        )    ;WHILE
;        (if (= enco2 1);
;          (progn
;            (setq numpun (busatr NNUPO "PUNTO"))
;            (setq espu (cdr (assoc 41 (entget nnupo))))
;          )
;        )
;        (COMMAND "ZOOM" "P")
;        (IF (= CONT 1)
;          (PROGN
;            (SETQ ENTX2 (SSNAME GPOTXTP 1))
;            (SETQ NUMEROINICIAL NUMPUN)
;            (SETQ NUMEROINICIAL2 NUMPUN)
;          )
;        )
;        (IF (> CONT 1)
;          (PROGN
;            (SETQ ENTX (SSNAME GPOTXTP 1))
;            (setq nte (STRCAT NUMEROINICIAL " - " NUMPUN))
;            (SETQ NUMEROINICIAL NUMPUN)
;            (entmod (subst (cons 1 nte) (assoc 1 (entget entx2)) (entget entx2)))
;            (SETQ ENTX2 ENTX)
;          )
;        )
;
    (SETQ CONT (1+ CONT))
  )  
;  (setq nte (STRCAT NUMEROINICIAL " - " NUMEROINICIAL2))
;  (entmod (subst (cons 1 nte) (assoc 1 (entget entx2)) (entget entx2)))

  (command "line" eii (strcat (RTOS X 2 4) "," (RTOS yfin 2 4) ) "")
  (command "copy" (entlast) "" "m" eii (strcat (RTOS (+ X 42.443) 2 4) "," (RTOS y 2 4)) (strcat (RTOS (+ X 90.950) 2 4) "," (RTOS y 2 4)) (strcat (RTOS (+ X 127.33) 2 4) "," (RTOS y 2 4)) (strcat (RTOS (+ X 173.174) 2 4) "," (RTOS y 2 4)) (strcat (RTOS (+ X 219.827) 2 4) "," (RTOS y 2 4)) (strcat (RTOS (+ X 268.334) 2 4) "," (RTOS y 2 4)) (strcat (RTOS (+ X 316.84) 2 4) "," (RTOS y 2 4)) (strcat (RTOS (+ X 355.646) 2 4) "," (RTOS y 2 4)) "")
;  (if (= (getvar "acadver") "17.1s (LMS Tech)")
;    (COMMAND "INSERt" (STRCAT RUTA "BLOCKS\\ENCABEZADO.dwg") (strcat (RTOS X 2 4) "," (RTOS yfin 2 4)) "")
    (COMMAND "INSERt" (STRCAT RUTA "BLOCKS\\ENCABEZADO.dwg") (strcat (RTOS X 2 4) "," (RTOS yfin 2 4)) "" "" "")
;  )
  (COMMAND "EXPLODE" (ENTLASt) "")
  (COMMAND "VIEW" "R" "PROV")
  (SETVAR "OSMODE" OPCIONESOS)
)

(defun CEROS (cadintercambio)
  (SETQ CADENAFINAL cadintercambio)
  (SETQ CONTDD 0)
  (REPEAT 10
    (setq cadenafinal (vl-string-subst (strcat "/0" (itoa contdd) "/") (strcat "/" (itoa contdd) "/") cadenafinal))
    (setq cadenafinal (vl-string-subst (strcat "/0" (itoa contdd) ".") (strcat "/" (itoa contdd) ".") cadenafinal))
    (setq contdd (1+ contdd))
  )
  (SETQ cadintercambio CADENAFINAL)
)

(defun qcomas (cadintercambio)
  (SETQ CARX (SUBSTR cadintercambio 1 1))
  (setq contadorx 1)
  (setq cadenadesalida "")
  (while (/= carx "")
    (SETQ CARX (SUBSTR cadintercambio contadorx 1))
    (if (/= carx ",") (setq cadenadesalida (strcat cadenadesalida carx)))
    (setq contadorx (1+ contadorx))
  )
  (setq cadenadesalida cadenadesalida)
)
(DEFUN SUMA (P VX VY)
  (SETQ XSUMA (CAR P))
  (SETQ YSUMA (CAR (CDR P)))
  (LIST (+ XSUMA VX) (+ YSUMA VY) (LAST P))
)

(DEFUN MPUNex (POLI)
  (C:LIBRERIA "SEPARA VALORES DE COMAS DE UN TEXTO TO LISTA")
  (SETQ TIPOPLANO (GETSTRING "\n TIPO DE PLANO? ('A'sentamientos/'U'so comun/'I'nterno/'P'arcela/'S'olar):"))
  (if (= (strcase tipoplano) "S")
    (progn
     (setq lescalas "100,200,500,1000,1500")
     (SETQ lescalas2 (SEPARA_VAL_COMAS lescalas))
    )
  )
  (if (= (strcase tipoplano) "P")
    (progn
     (setq lescalas "200,500,1000,2500,5000,10000,20000,50000,75000,100000")
     (SETQ lescalas2 (SEPARA_VAL_COMAS lescalas))
    )
  )
  (if (= (strcase tipoplano) "I")
    (progn
     (setq lescalas "1000,2500,5000,10000,20000,40000,50000,100000,125000,150000,175000,200000")
     (SETQ lescalas2 (SEPARA_VAL_COMAS lescalas))
    )
  )
  (if (= (strcase tipoplano) "U")
    (progn
     (setq lescalas "500,1000,2500,5000,10000,20000,50000,100000,125000,150000,175000,200000")
     (SETQ lescalas2 (SEPARA_VAL_COMAS lescalas))
    )
  )
  (if (= (strcase tipoplano) "A")
    (progn
     (setq lescalas "500,1000,2500,5000")
     (SETQ lescalas2 (SEPARA_VAL_COMAS lescalas))
    )
  )
  (setq poli (car (entsel "\n Selecciona la poligonal envolvente: ")))
  (SETQ PROV 1)
  (SETQ P1T (VERTICE POLI PROV))
  (SETQ XMENOR (CAR P1T))
  (SETQ YMENOR (CADR P1T))
  (SETQ XMAYOR XMENOR)
  (SETQ YMAYOR YMENOR)
  (SETQ PROVV P1T)
  (while p1t
    (SETQ X2PROV (CAR P1T))
    (SETQ Y2PROV (CADR P1T))
    (IF (AND (< X2PROV XMENOR) (/= X2PROV nil)) (SETQ XMENOR X2PROV))
    (IF (AND (< Y2PROV YMENOR) (/= Y2PROV nil)) (SETQ YMENOR Y2PROV))
    (IF (AND (> X2PROV XMAYOR) (/= X2PROV nil)) (SETQ XMAYOR X2PROV))
    (IF (AND (> Y2PROV YMAYOR) (/= Y2PROV nil)) (SETQ YMAYOR Y2PROV))
    (SETQ PROV (1+ PROV))
    (SETQ P1T (VERTICE POLI PROV))
  )
  (setq dosx (* (- xmayor xmenor) 0.30))
  (setq dosy (* (- ymayor ymenor) 0.30))
  (COMMAND "ZOOM" "W" (STRCAT (RTOS (- XMENOR dosx) 2 6) "," (RTOS (- YMENOR dosy) 2 6)) (STRCAT (RTOS (+ XMAYOR dosx) 2 6) "," (RTOS (+ YMAYOR dosy) 2 6))) 
  (REDRAW POLI 3)
  (if (< (/ (- ymayor ymenor) (- xmayor xmenor)) 0.92857)
    (PROGN
      (setq dsten (- xmayor xmenor))
      (setq escalal (cdr (assoc 1 lescalas2)))
      (setq cont 2)
      (while escalal
        (setq comprob (fix (/ dsten (* 0.84 escalal))))
        (if (/= comprob 1) 
          (progn 
            (setq escalal (cdr (assoc cont lescalas2)))
            (setq cont (1+ cont))
          )
        )
        (if (= comprob 1) 
          (setq escalal NIL)
        )
      )
    )
    (PROGN
      (setq dsten (- ymayor ymenor))
      (setq escalal (cdr (assoc 1 lescalas2)))
      (setq cont 2)
      (while escalal
        (setq comprob (fix (/ dsten (* 0.78 escalal))))
        (if (/= comprob 1) 
          (progn 
            (setq escalal (cdr (assoc cont lescalas2)))
            (setq cont (1+ cont))
          )
        )
        (if (= comprob 1) 
          (setq escalal NIL)
        )
      )
    )
  )
  

  (SETQ PROV 1)
  (SETQ P1T (VERTICE POLI PROV))
  (WHILE P1T
    (setq gpoLP (ssget "C" (suma p1T 0.10 0.10) (suma p1T -0.10 -0.10)))
    (SETQ R (sslength gpoLP))
    (SETQ PROV2 0)
    (setq mdist 100)
    (SETQ OBCOR NIL)
    (REPEAT R
      (SETQ OBJP (ssname gpoLP PROV2))
      (if (= "PUNTO" (cdr (assoc 2 (entget OBJP))))
       (progn
        (SETQ PVT (cdr (assoc 10 (entget OBJP))))
        (setq pdist (distance p1T pvT))
        (if (> mdist pdist)
         (progn
          (setq mdist pdist)
          (setq obcor objP)
         )
        )
       )
      )
      (SETQ PROV2 (1+ PROV2))
    )
    (if (AND (< 0 MDIST) (/= obcor nil))
    (if (= noterr "1")
     (IF (> MDIST 0.01)
      (PROGN
       (ALERT "HAY UN BLOCK FUERA DE SU POSICION")
       (SETQ XYZ (cdr (assoc 10 (ENTGET OBCOR))))
       (COMMAND "ZOOM" "C" XYZ "4")
       (COMMAND "CIRCLE" XYZ ".1")
       (SETQ PROVE (ENTLAST))
       (setQ OPT (GETSTRING "DESEAS MOVERLO HACIA LA LINEA (S/N) <S> :"))
       (IF (= "CIRCLE" (cdr (assoc 0 (ENTGET PROVE))))
         (COMMAND "ERASE" PROVE "")
       )
       (IF (= OPT "")
          (SETQ OPT "S") 
       )
       (IF (= OPT "S")
        (PROGN
         (command "MOVE" OBCOR "" (cdr (assoc 10 (entget OBCOR))) P1T)
        )
       )
       (COMMAND "ZOOM" "P")
      )
     )
      (if (= oppdesf "1")
        (command "MOVE" OBCOR "" (cdr (assoc 10 (entget OBCOR))) P1T)
      )
     )
    )
    (SETQ PROV (1+ PROV))
    (SETQ P1T (VERTICE POLI PROV))
    (IF (AND (/= P1T NIL) (/= PROVV NIL))
     (PROGN
      (setq pRdist (distance p1T PROVV))
      (IF (= PRDIST 0)
       (PROGN
        (ALERT "TIENES UNA DISTANCIA 'CERO' EN DOS VERTICES DISTINTOS")
        (command "ZOOM" "C" P1T 10)
        (COMMAND "CIRCLE" P1T "5")
        (FINISH)
       )
      )
      (SETQ PROVV P1T)
     )
    )
  )         
)

(defun verticeSURF (poli nov)
  (setq listap (entget poli))
  (setq nver 0)
  (setq salir "N")
  (while (= salir "N")
    (setq sublisp (car listap))
    (if (= 10 (car sublisp))
      (progn
        (setq punto (cdr sublisp))   
        (setq nver (+ nver 1))
      )
    )
    (setq listap (cdr listap))
    (if listap
      (setq salir "N")
      (setq salir "S")
    )
    (if (= nov nver)
      (setq salir "S")
    )
  )
  (if (not listap)
    (setq punto nil)
  )
  (setq punto punto)
)
