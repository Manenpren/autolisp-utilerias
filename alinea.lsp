(defun c:alinsec ()
  (print "\n Seleciona los elementos a procesar ")
  (setq gpo(ssget))
  (setq gpoo (ssadd))
  (filtroali gpo)
  (ordenALIN)
  (SETQ R 0)
  (setq ob (ssname gpo R))
  (WHILE OB
    (IF (= "INSERT" (cdr (assoc 0 (entget ob))))
      (PROGN
        (setq PUNTO (cdr (assoc 10 (entget OB))))
        (COMMAND "MOVE" OB "" PUNTO "PER" (cdr (assoc 10 (entget (ssname gpoo 0)))))
        (setq R (+ R 1))
        (setq ob (ssname gpo R))
      )
    )
  )
)

(defun ordenALIN ()
  (setq ele 0)
  (setq ob (ssname gpo ele))
  (SETQ ELIMINADOS "")
  (while ob
    (if (= "LINE" (cdr (assoc 0 (entget ob))))
      (setq numli ELE)
    )
;    (if (OR (= "LWPOLYLINE" (cdr (assoc 0 (entget ob)))) (= "POINT" (cdr (assoc 0 (entget ob)))) (AND (= "INSERT" (cdr (assoc 0 (entget ob)))) (= "PUNTO" (cdr (assoc 1 (entget ob))))))
;      (SETQ ELIMINADOS (STRCAT ELIMINADOS (ITOA ELE) ","))
;    )
    (setq ele (+ ele 1))
    (setq ob (ssname gpo ele))
  )
;  (IF (/= "" ELIMINADOS)
;   (SETQ LNG (STRLEN ELIMINADOS))
;   (SETQ R 0)
;   (REPEAT LNG
;      (SETQ R (+ R 1))
;   )
;  )
  (setq gpoo (ssadd (ssname gpo numli)))
  (ssdel (ssname gpo numli) gpo)
)

(defun filtroali (gpo)
  (setq cof 0)
  (setq cuelin 0)
  (setq cuetex 0)
  (while (/= cof (sslength gpo))
    (setq eliobj "SI")
    (setq objfil (ssname gpo cof))
    (if (= "LINE" (cdr (assoc 0 (entget objfil))))
      (progn
        (setq eliobj "NO")
        (setq cuelin (+ cuelin 1)) 
      ) 
    )
    (if (= "PUN2" (cdr (assoc 2 (entget objfil))))
      (setq eliobj "NO")
    )
    (if (= eliobj "SI")
      (progn
        (ssdel objfil gpo)
        (setq cof (- cof 1))
      )
    )
    (setq cof (+ cof 1))
  )

  (if (> cuelin 1)
    (progn
      (alert "Se seleccionaron mas de una linea en el grupo")
      (setq tipent "X") 
      (while (/= "LINE" TipEnt)
        (setq lin (car (entsel "Selecciona la linea correspondiente")))
        (setq TipEnt (cdr (assoc 0 (entget lin)))) 
        (if (/= "LINE" TipEnt)
          (alert "La entidad que seleccionaste no es una linea")
        ) 
      ) 
      (setq gpo (agrega lin gpo))
    )
  )

  (if (= cuelin 0)
    (progn
      (alert "No se selecciono la linea de la seccion")
      (setq tipent "X") 
      (while (/= "LINE" TipEnt)
        (setq lin (car (entsel "Selecciona la linea correspondiente")))
        (setq TipEnt (cdr (assoc 0 (entget lin)))) 
        (if (/= "LINE" TipEnt)
          (alert "La entidad que seleccionaste no es una linea")
        ) 
      ) 
      (setq gpo (agrega lin gpo))
    )
  )

  (setq filtrovar gpo)  
)

(defun agrega (entagr gpoagr)
  (setq tipagr (cdr (assoc 0 (entget entagr))))
  (setq cueagr 0)
  (while (/= cueagr (sslength gpoagr))
    (setq nomagr (ssname gpoagr cueagr))
    (if (= tipagr (cdr (assoc 0 (entget nomagr))))
      (progn
        (ssdel nomagr gpoagr)
        (setq cueagr (- cueagr 1))
      ) 
    )
    (setq cueagr (+ cueagr 1))
  )
  (ssadd entagr gpoagr)
  (setq agregavar gpoagr)
)
