(defun c:SAF ()
  (C:LIBRERIA "BUSCA VALOR DE ATRIBUTO")
  (C:LIBRERIA "AREA OBTENIDA EN UN PUNTO")
  (C:LIBRERIA "ASOCIASIONES")
  (COMMAND "UNDO" "M")
  (COMMAND "VIEW" "S" "C")
  (setq PROV (CAR (ENTSEL "SELECCIONA BLOCK")))
  (setq NOMBLO (cdr (assoc 2 (entget PROV))))
  (COMMAND "INSERT" NOMBLO "0,0" "" "" "")
  (SETQ X (ENTLAST))
  (COMMAND "EXPLODE" X "")
  (SETQ GPOA (SSGET "P"))
  (SETQ GPOXX (SSADD))
  (SETQ P 0)
  (SETQ AREACORTE "0")
  (SETQ ATERRAP "0")
  (SETQ AD "0")
  (WHILE (/= (cdr (assoc 0 (entget PROV))) "TEXT")
    (SETQ PROV (SSNAME GPOA P))
    (SETQ P (1+ P))
  )
    (IF (= (cdr (assoc 0 (entget PROV))) "TEXT")
      (PROGN
        (SETQ VTEXT (cdr (assoc 1 (entget PROV))))
        (IF (AND (= (SUBSTR VTEXT 1 2) "Rs") (= VRAS NIL))
          (SETQ VRAS (SUBSTR VTEXT 3 (- (STRLEN VTEXT) 2)))
        )
        (IF (AND (= (SUBSTR VTEXT 1 2) "Tn") (= VTN NIL))
          (SETQ VTN (SUBSTR VTEXT 3 (- (STRLEN VTEXT) 2)))
        )
      )
    )
  (setq XY (cdr (assoc 10 (entget PROV))))
  (SETQ Y (CADR XY))
  (SETQ XY (STRCAT "0," (RTOS Y)))
  (COMMAND "ZOOM" "C" XY "30")
  (SETQ AFI 0)
  (SETQ ABA 0)
  (SETQ ACA 0)
  (SETQ NOMBREP nil)
  (SETQ NOMBREP2 nil)
  (SETQ NOMBREP3 nil)
  (SETQ NOMBREP4 nil)
  (SETQ AREAP nil)
  (SETQ AREAP2 nil)
  (SETQ AREAP3 nil)
  (SETQ AREAP4 nil)
  (SETQ P 0)
  (SETQ PROV (SSNAME GPOA P))
  (WHILE (/= (cdr (assoc 0 (entget PROV))) "INSERT")
    (SETQ P (1+ P))
    (IF (/= PROV nil)
     (SETQ PROV (SSNAME GPOA P))
    )
  )
  (IF (/= PROV nil)
   (PROGN
    (SSADD PROV GPOXX)
    (SETQ NOMBREP (BUSATR PROV "NOMBRE"))  
    (SETQ AREAP (BUSATR PROV "AREA"))  
;    (COMMAND "ERASE" PROV "")
   )
  )
  (SETQ P (1+ P))
  (SETQ PROV (SSNAME GPOA P))
  (IF (/= PROV nil)
   (PROGN
    (SETQ ATT (cdr (assoc 0 (entget PROV))))
    (WHILE (AND (/= ATT "INSERT") (/= PROV nil))
      (SETQ P (1+ P))
      (SETQ PROV (SSNAME GPOA P))
      (IF (/= PROV nil)
        (SETQ ATT (cdr (assoc 0 (entget PROV))))
      )
    )
    (IF (/= PROV nil)
     (PROGN
      (SETQ NOMBREP2 (BUSATR PROV "NOMBRE"))  
      (SETQ AREAP2 (BUSATR PROV "AREA"))  
      (SSADD PROV GPOXX)
;      (COMMAND "ERASE" PROV "")
     )
    )
   )
  )
  (SETQ P (1+ P))
  (SETQ PROV (SSNAME GPOA P))
  (IF (/= PROV nil)
   (PROGN
    (SETQ ATT (cdr (assoc 0 (entget PROV))))
    (WHILE (AND (/= ATT "INSERT") (/= PROV nil))
      (SETQ P (1+ P))
      (SETQ PROV (SSNAME GPOA P))
      (IF (/= PROV nil)
        (SETQ ATT (cdr (assoc 0 (entget PROV))))
      )
    )
    (IF (/= PROV nil)
     (PROGN
      (SETQ NOMBREP3 (BUSATR PROV "NOMBRE"))  
      (SETQ AREAP3 (BUSATR PROV "AREA"))  
      (SSADD PROV GPOXX)
;      (COMMAND "ERASE" PROV "")
     )
    )
   )
  )
  (SETQ P (1+ P))
  (SETQ PROV (SSNAME GPOA P))
  (IF (/= PROV nil)
   (PROGN
    (SETQ ATT (cdr (assoc 0 (entget PROV))))
    (WHILE (AND (/= ATT "INSERT") (/= PROV nil))
      (SETQ P (1+ P))
      (SETQ PROV (SSNAME GPOA P))
      (IF (/= PROV nil)
        (SETQ ATT (cdr (assoc 0 (entget PROV))))
      )
    )
    (IF (/= PROV nil)
     (PROGN
      (SETQ NOMBREP4 (BUSATR PROV "NOMBRE"))  
      (SETQ AREAP4 (BUSATR PROV "AREA"))  
      (SSADD PROV GPOXX)
;      (COMMAND "ERASE" PROV "")
     )
    )
   )
  )
  (IF (= NOMBREP "CORTE") (SETQ AREACORTE AREAP))
  (IF (= NOMBREP "TERRAP") (SETQ ATERRAP AREAP))
  (IF (= NOMBREP "DESP") (SETQ AD AREAP))
  (IF (= NOMBREP2 "CORTE") (SETQ AREACORTE AREAP2))
  (IF (= NOMBREP2 "TERRAP") (SETQ ATERRAP AREAP2))
  (IF (= NOMBREP2 "DESP") (SETQ AD AREAP2))
  (IF (= NOMBREP3 "CORTE") (SETQ AREACORTE AREAP3))
  (IF (= NOMBREP3 "TERRAP") (SETQ ATERRAP AREAP3))
  (IF (= NOMBREP3 "DESP") (SETQ AD AREAP3))
  (IF (= NOMBREP4 "CORTE") (SETQ AREACORTE AREAP4))
  (IF (= NOMBREP4 "TERRAP") (SETQ ATERRAP AREAP4))
  (IF (= NOMBREP4 "DESP") (SETQ AD AREAP4))
;  (SETQ PINS (GETPOINT "DAME EL PUNTO DE INSERCION DE LAS AREAS "))
  (COMMAND "INSERT" "AREAS" PAUSE ".2" ".2" "" "0+000" "1" "1" "1" "1" "1" "1" "1" "1" "1" "1" "1" "" "" "" "" "" "" "" "" "" "" "")
; AREACORTE AFI ABA ACA ABN
  (SSADD (ENTLAST) GPOA)
  (setq bl (entnext (ENTLAST)))
  (COMMAND "attedit" "" "" "" "" bl "V" "R" NOMBLO "")
  (setq bl (entnext BL))
  (COMMAND "attedit" "" "" "" "" bl "V" "R" VRAS "")
  (setq bl (entnext BL))
  (COMMAND "attedit" "" "" "" "" bl "V" "R" VTN "")
  (setq bl (entnext BL))
  (COMMAND "attedit" "" "" "" "" bl "V" "R" (RTOS (ATOF AD) 2 3) "")
  (setq bl (entnext BL))
  (COMMAND "attedit" "" "" "" "" bl "V" "R" (RTOS (ATOF AREACORTE) 2 3) "")
  (setq bl (entnext BL))
  (COMMAND "attedit" "" "" "" "" bl "V" "R" (RTOS (ATOF ATERRAP) 2 3) "")
  (setq bl (entnext BL))
  (COMMAND "attedit" "" "" "" "" bl "V" "R" "1.800" "")
  (setq bl (entnext BL))
  (COMMAND "attedit" "" "" "" "" bl "V" "R" "1.200" "")
  (setq bl (entnext BL))
  (COMMAND "attedit" "" "" "" "" bl "V" "R" "1.200" "")
  (setq bl (entnext BL))
  (COMMAND "attedit" "" "" "" "" bl "V" "R" "0.420" "")
  (setq bl (entnext BL))
  (COMMAND "attedit" "" "" "" "" bl "V" "R" "0.255" "")
  (command "layer" "t" "*" "")
  (COMMAND "BLOCK" NOMBLO "Y" "0,0" GPOA "R" GPOXX "")
  (COMMAND "ERASE" GPOXX "")
  (COMMAND "VIEW" "R" "C")
)
