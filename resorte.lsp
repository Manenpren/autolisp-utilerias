(defun c:rst ()
  (setq radio (getreal "\n Radio de resorte : "))
  (setq sept (getreal "\n Constate de separacion de resorte : "))
  (setq pto (getpoint "\n Dame el punto base del resorte"))
  (setq int (getreal "\n Intervalo del tiempo"))
  (setq rev (getreal "\n revoluciones "))
  (setq cont 0)
  (setq rev2 (* 6.283185307 rev))
  (command "3dpoly")
  (while (< cont rev2)
    (setq x (* radio (cos cont)))
    (setq y (* radio (sin cont)))
    (setq z (* cont sept))
    (setq xyz (list x y z))
    (setq x2 (* -1 radio (sin cont)))
    (setq y2 (* radio (cos cont)))
    (setq z2 sept)
    (setq xyz2 (list x2 y2 z2))
    (setq x3 (* radio (cos cont) (expt (+ (* radio radio) (* sept sept)) -0.5)))
    (setq y3 (* radio (sin cont) (expt (+ (* radio radio) (* sept sept)) -0.5)))
    (setq z3 0)
    (setq xyz3 (list x3 y3 z3))
    (command xyz)
    (setq cont (+ int cont))
  )
  (setq cont rev2)
  (setq x (* radio (cos cont)))
  (setq y (* radio (sin cont)))
  (setq z (* cont sept))
  (setq xyz (list x y z))
  (command xyz)
  (command "")
)
