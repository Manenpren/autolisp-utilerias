(defun C:ea ()
    (setq TEXTO (car (entsel "Selecciona La cota: ")))
    (setq sec (cdr (assoc 1 (entget TEXTO))))
    (repeat 4
        (setq bl (car (entsel "Selecciona EL BLOCK: ")))
        (setq bl (entnext bl))
        (setq nombre (cdr (assoc 1 (entget bl))))
        (if (= "BASE" (substr nombre 1 4))
            (setq nom (strcat (substr nombre 1 4) "-" sec "-A" ))
        )
        (if (= "SUBR" (substr nombre 1 4))
            (setq nom (strcat (substr nombre 1 10) "-" sec "-A"))
        )
        (if (= "FILT" (substr nombre 1 4))
            (setq nom (strcat (substr nombre 1 6) "-" sec "-A"))
        )
        (if (= "CARP" (substr nombre 1 4))
            (setq nom (strcat (substr nombre 1 7) "-" sec "-A"))
        )
        (COMMAND "attedit" "" "nomar" "" "" bl "V" "R" nom "")
    )
)
