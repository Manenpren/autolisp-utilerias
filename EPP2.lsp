(defun vertice (poli nov)
  (setq listap (entget poli))
  (setq nver 0)
  (setq salir "N")
  (while (= salir "N")
    (setq sublisp (car listap))
    (if (= 10 (car sublisp))
      (progn
        (setq punto (cdr sublisp))   
        (setq nver (+ nver 1))
      )
    )
    (setq listap (cdr listap))
    (if listap
      (setq salir "N")
      (setq salir "S")
    )
    (if (= nov nver)
      (setq salir "S")
    )
  )
  (if (not listap)
    (setq punto nil)
  )
  (setq punto punto)
)


(defun c:EPP2 ()
  (setq NomArch (getfiled "ARCHIVO A CREAR " "*." "CSV" 19))
  (write-line "Selecciona las polylineas a procesar")
  (setq GpoPol (ssget))
  (setq Arch (open NomArch "w"))
  (setq cuenta 0)
  (while (/= cuenta (sslength GpoPol))
    (setq e (ssname GpoPol cuenta))
    (if (= "LWPOLYLINE" (cdr (assoc 0 (entget e))))
      (progn
        (setq nnver 1)
        (while (vertice e nnver)
          (setq vvert (vertice e nnver))
          (SETQ vY (CADR vvert))
          (SETQ vY (RTOS vY 2 3))
          (SETQ vX (CAR vvert))
          (SETQ vX (RTOS vX 2 3))
          (SETQ vZ (RTOS (cdr (assoc 38 (entget e))) 2 3))
          (write-line (strcat (rtos nnver 2 0) "," vx "," vy "," vz "," (cdr (assoc 8 (entget e)))) Arch)
          (setq nnver (+ nnver 1))
        )
      )
    )
    (setq cuenta (+ cuenta 1))
  )
  (close arch)
)
