(DEFUN C:SIMAR ()
  (C:LIBRERIA "SEARCH OBJ GPO")
  (C:LIBRERIA "BUSCA VALOR DE ATRIBUTO")
  (C:LIBRERIA "AREA OBTENIDA EN UN PUNTO")
  (C:LIBRERIA "ASOCIASIONES")
  (COMMAND "UNDO" "M")
  (COMMAND "VIEW" "S" "C")
  (setq PROV (CAR (ENTSEL "SELECCIONA BLOCK")))
  (setq NOMBLO (cdr (assoc 2 (entget PROV))))
  (COMMAND "INSERT" NOMBLO "0,0" "" "" "")
  (SETQ X (ENTLAST))
  (COMMAND "EXPLODE" X "")
  (SETQ GPOA (SSGET "P"))
  (SETQ P 0)
  (WHILE (/= (cdr (assoc 0 (entget PROV))) "TEXT")
    (SETQ PROV (SSNAME GPOA P))
    (SETQ P (1+ P))
  )
  (setq XY (cdr (assoc 10 (entget PROV))))
  (command "layer" "fr" "tn" "")
  (command "layer" "fr" "gslayer" "")
  (command "layer" "fr" "curvas" "")
  (SETQ Y (CADR XY))
  (SETQ XY (STRCAT "0," (RTOS Y)))
  (COMMAND "ZOOM" "C" XY "30")
  (C:1)
  (SETQ AREACORTE 0)
  (SETQ AFI 0)
  (SETQ ABA 0)
  (SETQ ACA 0)
  (SETQ ABN 0)
;  (WHILE (/= NOMBRE "CORTE")
;    (SETQ NOBJ (S_OBJ_GPO GPO NINICIO 2 "NOMAR" OBR)) 
;    (SETQ PROV (SSNAME GPOA NOBJ))
;    (SETQ NOMBRE (BUSATR PROV "NOMBRE"))
;    (SETQ NINICIO (1+ OBR))
;  )
;  (SETQ AREACORTE (BUSATR PROV "AREA"))
;  (COMMAND "ERASE" PROV "")

;SECCION DE BUSQUEDA DE BLOCKS CON AREAS
  (SETQ NOMBREP nil)
  (SETQ NOMBREP2 nil)
  (SETQ NOMBREP3 nil)
  (SETQ AREAP nil)
  (SETQ AREAP2 nil)
  (SETQ AREAP3 nil)
  (SETQ P 0)
  (SETQ PROV (SSNAME GPOA P))
  (setq p (1+ p))
  (WHILE (/= (cdr (assoc 0 (entget PROV))) "INSERT")
    (IF (/= PROV nil)
     (SETQ PROV (SSNAME GPOA P))
    )
    (SETQ P (1+ P))
  )
  (IF (/= PROV nil)
   (PROGN
    (SSDEL PROV GPOA)
    (SETQ NOMBREP (BUSATR PROV "NOMBRE"))  
    (SETQ AREAP (BUSATR PROV "AREA"))  
    (COMMAND "ERASE" PROV "")
   )
  )
  (setq p (1- p))
  (SETQ PROV (SSNAME GPOA P))
  (IF (/= PROV nil)
   (PROGN
    (SETQ ATT (cdr (assoc 0 (entget PROV))))
    (WHILE (AND (/= ATT "INSERT") (/= PROV nil))
      (SETQ PROV (SSNAME GPOA P))
      (IF (/= PROV nil)
        (SETQ ATT (cdr (assoc 0 (entget PROV))))
      )
      (SETQ P (1+ P))
    )
    (IF (/= PROV nil)
     (PROGN
      (SETQ NOMBREP2 (BUSATR PROV "NOMBRE"))  
      (SETQ AREAP2 (BUSATR PROV "AREA"))  
      (SSDEL PROV GPOA)
      (COMMAND "ERASE" PROV "")
     )
    )
   )
  )
  (IF (/= PROV nil)
   (PROGN
    (SETQ ATT (cdr (assoc 0 (entget PROV))))
    (WHILE (AND (/= ATT "INSERT") (/= PROV nil))
      (SETQ PROV (SSNAME GPOA P))
      (IF (/= PROV nil)
        (SETQ ATT (cdr (assoc 0 (entget PROV))))
      )
      (SETQ P (1+ P))
    )
    (IF (/= PROV nil)
     (PROGN
      (SETQ NOMBREP2 (BUSATR PROV "NOMBRE"))  
      (SETQ AREAP2 (BUSATR PROV "AREA"))  
      (SSDEL PROV GPOA)
      (COMMAND "ERASE" PROV "")
     )
    )
   )
  )

  (IF (/= NOMBREP nil)
    (IF (AND (= (STRCASE NOMBREP) "CORTE") (= NOMBREP2 nil))
      (PROGN
        (SETQ AREACORTE AREAP)
        (SETQ AREATERRAP 0)
      )
    )
  )
  (IF (AND (/= NOMBREP nil) (/= NOMBREP2 nil))
    (IF (AND (= (STRCASE NOMBREP) "CORTE") (= (STRCASE NOMBREP2) "TERRAP"))
      (PROGN
        (SETQ AREACORTE AREAP) 
        (SETQ AREATERRAP AREAP2)
      )
    )
  )
  (IF (/= NOMBREP2 nil)
    (IF (AND (= NOMBREP nil) (= (STRCASE NOMBREP2) "TERRAP"))
      (PROGN
        (SETQ AREACORTE 0)
        (SETQ AREATERRAP AREAP2)
      )
    )
  )
  (IF (/= NOMBREP nil)
    (IF (AND (= (STRCASE NOMBREP) "TERRAP") (= NOMBREP2 nil))
      (PROGN
        (SETQ AREATERRAP AREAP)
        (SETQ AREACORTE 0)
      )
    )
  )
  (IF (AND (/= NOMBREP nil) (/= NOMBREP2 nil))
    (IF (AND (= (STRCASE NOMBREP) "TERRAP") (= (STRCASE NOMBREP2) "CORTE"))
      (PROGN
        (SETQ AREATERRAP AREAP)
        (SETQ AREACORTE AREAP2)
      )
    )
  )
  (IF (/= NOMBREP2 nil)
    (IF (AND (= NOMBREP nil) (= (STRCASE NOMBREP2) "CORTE"))
      (PROGN
        (SETQ AREATERRAP 0)
        (SETQ AREACORTE AREAP2)
      )
    )
  )



;;  (SETQ CORTE (CAR (ENTSEL "SELECCIONA BLOCK DE CORTE")))
;;  (SETQ AREACORTE (BUSATR CORTE "AREA"))  
;;  (COMMAND "ERASE" CORTE "")
;;  (setq ELPROY (CAR (ENTSEL "SELECCIONA EL TEXTO DE ELEVACION DE PROYECTO")))
  (SETQ ELPROY (GETPOINT "primer filtro "))
  (SETQ ELPROY2 (GETPOINT "segundo filtro "))
  (SETQ ELEBASE (CADR ELPROY))
;  (COMMAND "ZOOM" "C" ELPROY "18")
     (COMMAND "-BOUNDARY" elproy "")
     (COMMAND "AREA" "E" "L" "ERASE" "L" "")
     (SETQ Aprov (GETVAR "AREA"))
     (COMMAND "-BOUNDARY" elproy2 "")
     (COMMAND "AREA" "E" "L" "ERASE" "L" "")
     (SETQ Aprov2 (GETVAR "AREA"))
     (setq areafil (rtos (+ aprov aprov2) 2 3))
  (C:2)
;  (COMMAND "ZOOM" "C" XY "25")
  (SETQ PINS (GETPOINT "DAME EL PUNTO DE INSERCION DE LAS AREAS "))
  (COMMAND "INSERT" "AREAS4" PINS "" "" "" "0+000" "1" "1" "1" "1" "1" "1" "" "" "" "" "" "" "")
; AREACORTE AFI ABA ACA ABN
  (SSADD (ENTLAST) GPOA)
  (setq bl (entnext (ENTLAST)))
  (COMMAND "attedit" "" "" "" "" bl "V" "R" NOMBLO "")
  (setq bl (entnext BL))
  (COMMAND "attedit" "" "" "" "" bl "V" "R" "1.260" "")
  (setq bl (entnext BL))
  (COMMAND "attedit" "" "" "" "" bl "V" "R" "3.600" "")
  (setq bl (entnext BL))
  (COMMAND "attedit" "" "" "" "" bl "V" "R" areafil "")
  (setq bl (entnext BL))
  (COMMAND "attedit" "" "" "" "" bl "V" "R" AREACORTE "")
  (setq bl (entnext BL))
  (COMMAND "attedit" "" "" "" "" bl "V" "R" AREATERRAP "")
  (setq bl (entnext BL))
  (COMMAND "attedit" "" "" "" "" bl "V" "R" "1.5599" "" "")
  (command "layer" "t" "*" "")
  (COMMAND "BLOCK" NOMBLO "Y" "0,0" GPOA "")
  (COMMAND "VIEW" "R" "C")
)
