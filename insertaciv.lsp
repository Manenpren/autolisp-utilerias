(defun c:is ()
    (setq texto (car (entsel "estacion ")))
    (setq NOMBLO (cdr (assoc 1 (entget TEXTO))))
    (setq elev2 (car (entsel "Selecciona el cadenamiento ")))
    (setq n2 (cdr (assoc 1 (entget elev2))))
    (command "insert" (STRCAT nomblo) "0,0" "" "" "")
    (COMMAND "EXPLODE" L "")
    (command "insert" (STRCAT n2) "0,0" "" "" "")
    (COMMAND "EXPLODE" L "")
    (command "CHANGE" texto elev2 "" "P" "C" "RED" "")
    (COMMAND "-LAYER" "F" "RETICULA" "")
)
