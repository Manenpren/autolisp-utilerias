(defun C:ESTACION ()
  (C:LIBRERIA "BUSCA VALOR DE ATRIBUTO")
  (setq ATRES (strcase (getSTRING "IDENTIFICADOR DEL BLOCK :")))
  (setq e (car (entsel "Selecciona el OBJETO a escalar: ")))
  (setq NBES (cdr (assoc 2 (entget e))))
  (setq ESCALA (cdr (assoc 41 (entget e))))
  (setq NSES (getREAL "PORCENTAJE DE ESCALAMIENTO :"))
  (SETQ E (ENTNEXT))
  (while E
    (setq XYZ (cdr (assoc 10 (entget E))))
    (if (= "INSERT" (cdr (assoc 0 (entget E))))
      (if (= NBES (cdr (assoc 2 (entget E))))
        (if (= ESCALA (cdr (assoc 41 (entget E))))
          (PROGN
            (SETQ ATR2 (STRCASE (BUSATR E "CODE")))
            (SETQ PS (STRCAT "*" ATRES "*"))
            (IF (WCMATCH ATR2 PS)
              (command "SCALE" E "" XYZ NSES)
            )
          )
        )
      )
    )
    (setq E (ENTNEXT E))
  )
)
