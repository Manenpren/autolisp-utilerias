(defun C:SIM ()
  (C:LIBRERIA "BUSCA VALOR DE ATRIBUTO")
  (COMMAND "UNDO" "M")
  (COMMAND "VIEW" "S" "C")
  (setq PROV (CAR (ENTSEL "SELECCIONA BLOCK")))
  (setq NOMBLO (cdr (assoc 2 (entget PROV))))
  (setq nb2 nomblo)
  (COMMAND "INSERT" NOMBLO "0,0" "" "" "")
  (SETQ X (ENTLAST))
  (COMMAND "EXPLODE" X "")
  (SETQ GPOA (SSGET "P"))
  (SETQ PROV (SSNAME GPOA 0))
  (SETQ P 1)
  (WHILE (/= (cdr (assoc 0 (entget PROV))) "INSERT")
    (SETQ PROV (SSNAME GPOA P))
    (SETQ P (1+ P))
  )
  (setq XY (cdr (assoc 10 (entget PROV))))
  (COMMAND "ZOOM" "C" XY "40")
  (SETQ PROV (SSNAME GPOA 0))
  (SETQ P 1)
  (SETQ ACORTE NIL)  
  (SETQ ATERRAP NIL)  
  (SETQ ADESP NIL)
  (SETQ VRAS NIL)
  (SETQ VTN NIL)
  (SETQ EAREAS NIL)
  (SETQ GPODEL (SSADD))
  (WHILE PROV
    (IF (AND (= (cdr (assoc 0 (entget PROV))) "INSERT") (= (cdr (assoc 2 (entget PROV))) "AREAS5"))
      (SETQ EAREAS PROV)
    )
    (IF (AND (= (cdr (assoc 0 (entget PROV))) "INSERT") (= (cdr (assoc 2 (entget PROV))) "NOMAR"))
      (PROGN
        (SETQ AREAB (BUSATR PROV "AREA"))
        (SETQ NOMBREB (BUSATR PROV "NOMBRE"))
        (IF (OR (= NOMBREB "CORTE") (= NOMBREB "corte"))
          (PROGN
            (SETQ ACORTE AREAB)
            (SETQ AREAB NIL)
            (SSADD PROV GPODEL)
          )
        )
        (IF (OR (= NOMBREB "DESP") (= NOMBREB "desp"))
          (PROGN
            (SETQ ADESP AREAB)
            (SETQ AREAB NIL)
            (SSADD PROV GPODEL)
          )
        )
        (IF (OR (= NOMBREB "TERRAP") (= NOMBREB "terrap"))
          (PROGN
            (SETQ ATERRAP AREAB)
            (SETQ AREAB NIL)
            (SSADD PROV GPODEL)
          )
        )
        (IF (AND (/= (strcase NOMBREB) "TERRAP") (/= (strcase NOMBREB) "CORTE") (/= (strcase NOMBREB) "DESP") (/= NOMBREB NIL))
          (PROGN
            (ALERT "BLOCK DE AREA INCORRECTO")
            (EXIT)
          )    
        )
      )
    )
    (IF (= (cdr (assoc 0 (entget PROV))) "TEXT")
      (PROGN
        (SETQ VTEXT (cdr (assoc 1 (entget PROV))))
        (IF (AND (= (SUBSTR VTEXT 1 2) "Rs") (= VRAS NIL))
          (SETQ VRAS (SUBSTR VTEXT 3 (- (STRLEN VTEXT) 2)))
        )
        (IF (AND (= (SUBSTR VTEXT 1 2) "Tn") (= VTN NIL))
          (SETQ VTN (SUBSTR VTEXT 3 (- (STRLEN VTEXT) 2)))
        )
      )
    )
    (SETQ PROV (SSNAME GPOA P))
    (SETQ P (1+ P))
  )
  (IF (OR (= VRAS NIL) (= VTN NIL)) (PROGN (ALERT "DATOS INCORRECTOS") (EXIT)))
  (IF (= ACORTE NIL)
    (SETQ ACORTE "0.00")
  )
  (IF (= ATERRAP NIL)
    (SETQ ATERRAP "0.00")
  )
  (IF (= ADESP NIL)
    (SETQ ADESP "0.00")
  )
  (SETQ PINS (GETPOINT "DAME EL PUNTO DE INSERCION DE LAS AREAS "))
  (COMMAND "INSERT" "AREAS" PINS "" "" "" "0+000" "1" "1" "1" "1" "1" "1" "1" "1" "" "" "" "" "" "" "" "" "")
; AREACORTE AFI ABA ACA ABN
  (SSADD (ENTLAST) GPOA)
  (SETQ EAREAS (ENTLAST))
  (setq bl (entnext EAREAS))
  (COMMAND "attedit" "" "" "" "" bl "V" "R" NOMBLO "")
  (setq bl (entnext BL))
  (COMMAND "attedit" "" "" "" "" bl "V" "R" VRAS "")
  (setq bl (entnext BL))
  (COMMAND "attedit" "" "" "" "" bl "V" "R" VTN "")
  (setq bl (entnext BL))
  (COMMAND "attedit" "" "" "" "" bl "V" "R" (RTOS (ATOF ACORTE) 2 3) "")
  (setq bl (entnext BL))
  (COMMAND "attedit" "" "" "" "" bl "V" "R" (RTOS (ATOF ATERRAP) 2 3) "")
  (setq bl (entnext BL))
  (COMMAND "attedit" "" "" "" "" bl "V" "R" "1.8" "")
  (setq bl (entnext BL))
  (COMMAND "attedit" "" "" "" "" bl "V" "R" "1.8" "")
  (setq bl (entnext BL))
  (COMMAND "attedit" "" "" "" "" bl "V" "R" "0.63" "")
  (setq bl (entnext BL))
  (COMMAND "attedit" "" "" "" "" bl "V" "R" "0.45" "")
 (COMMAND "BLOCK" NOMBLO "Y" "0,0" GPOA "R" GPODEL "")
  (COMMAND "ERASE" GPODEL "")
  (COMMAND "VIEW" "R" "C")
)
