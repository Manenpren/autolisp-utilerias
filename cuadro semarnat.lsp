(defun c:ccsemarnat ()
  (command "undo" "m")
  (COMMAND "VIEW" "S" "PROV")
  (SETQ OPCIONESOS (GETVAR "OSMODE"))
  (COMMAND "DIMZIN" 1)
  (command "osnap" "none")
  (COMMAND "LUNITS" 2)
  (COMMAND "LUPREC" 3)
  (COMMAND "AUNITS" 4)
  (COMMAND "AUPREC" 4)
  (COMMAND "ANGDIR" 0)
  (COMMAND "ANGBASE" 0.0)
  (C:LIBRERIA "BUSCA VALOR DE ATRIBUTO")
  (C:LIBRERIA "vertices de una lwpolyline to var")
  (C:LIBRERIA "revisa polilynea ceros,bloques  y zoom")
  (C:LIBRERIA "encuentra block mas cercano a punto")
  (setq lin (car (entsel "\n Selecciona la polylinea a procesar: ")))
  (COMMAND "AREA" "E" LIN)
  (while (/= "LWPOLYLINE" (cdr (assoc 0 (entget lin))))
      (if (/= "LWPOLYLINE" (cdr (assoc 0 (entget lin))))
        (progn   
          (alert "\nEl objeto debe ser polylinea ")
          (setq lin (car (entsel "\n Selecciona objeto: ")))
        )
      )
  )
 (mpun lin)
 (COMMAND "AREA" "E" LIN)
 (setq mvertices (verticebd lin))
 (setq verpol1 (cdr (assoc 0 mvertices)))
 (setq block1 (blocktopto verpol1 0.01))
 (setq xpol1 (rtos (car verpol1) 2 3))
 (setq ypol1 (rtos (car (cdr verpol1)) 2 3))
 (setq codigo1 (BUSATR block1 "PUNTO"))
 (if (= codigo1 nil) (alert "block sin atributo de codigo"))
 (setq elevacion1 (BUSATR block1 "ELEV"))
 (if (= elevacion1 nil) (BUSATR NOMOBJ "ELEVACION"))
 (if (= elevacion1 nil) (alert "block sin atributo de elevacion"))
 (setq cuever 1)
 (SETQ matrizcuadro NIL)
 (setq verpol 1)
 (setq blocki block1)
 (setq xpoli xpol1)
 (setq ypoli ypol1)
 (setq codigoi codigo1)
 (setq elevacioni elevacion1)
 (setq verpoli verpol1)
 (while verpol
   (setq verpol (cdr (assoc cuever mvertices)))
   (IF (/= VERPOL NIL)
    (PROGN
     (setq block (blocktopto verpol 0.01))
     (setq xpol (rtos (car verpol) 2 3))
     (setq ypol (rtos (car (cdr verpol)) 2 3))
     (setq codigo (BUSATR block "PUNTO"))
     (if (= codigo nil) (alert "block sin atributo de codigo"))
     (setq elevacion (BUSATR block "ELEV"))
     (if (= elevacion nil) (BUSATR block "ELEVACION"))
     (if (= elevacion nil) (alert "block sin atributo de elevacion"))
     (setq elevacion (rtos (atof elevacion) 2 3))
     (setq a (angtos (angle verpol1 verpol)))
     (setq aa (formato a))
     (setq renglon (list (cons 4 (strcat codigo1 "-" codigo)) (cons 0 (rtos (distance verpol1 verpol) 2 3)) (cons 1 aa) (cons 5 codigo1) (cons 3 Ypol1) (cons 2 Xpol1) (cons 6 elevacion1)))
     (setq CONCATENADO (cons cuever renglon))
     (setq matrizcuadro (append matrizcuadro (list CONCATENADO)))
     (setq cuever (+ cuever 1))
     (setq block1 block)
     (setq xpol1 xpol)
     (setq ypol1 ypol)
     (setq codigo1 codigo)
     (setq elevacion1 elevacion)
     (setq verpol1 verpol)
    )
   ) ;IF
 );WHILE
 (alert "llegue")
 (setq a (angtos (angle verpol1 verpolI)))
 (setq aa (formato a))
 (setq renglon (list (cons 4 (strcat codigo1 "-" codigoi)) (cons 0 (rtos (distance verpol1 verpolI) 2 3)) (cons 1 aa) (cons 5 codigo1) (cons 3 Ypol1) (cons 2 Xpol1) (cons 6 elevacion1)))
 (setq CONCATENADO (cons cuever renglon))
 (setq matrizcuadro (append matrizcuadro (list CONCATENADO)))
 (SETQ PDESCARGA (GETPOINT "ESQUINA INFERIOR IZQUIERDA DEL CUADRO :"))
 (setq pdescarga2 pdescarga)
 (SETQ ALTURA (* CUEVER 1.25))
 (SETQ P2 (SUMA PDESCARGA 44.887 (+ ALTURA 5.556)))
 (SETQ XYZ (SUMA PDESCARGA 0 ALTURA))
 (command "zoom" pdescarga p2)
 (COMMAND "INSERt" (STRCAT RUTA "BLOCKS\\cdsemarnat.dwg") xyz "" "" "")
 (COMMAND "EXPLODE" (ENTLASt) "")
 (setq punretx (cons 10 pdescarga))
 (setq punretx2 (cons 11 xyz))
 (ENTMAKE (LIST '(0 . "LINE") '(100 . "AcDbEntity") '(100 . "AcDbLine") PUNRETX PUNRETX2))
 (SETQ P1 (SUMA PDESCARGA 44.887 0))
 (SETQ P12 (SUMA PDESCARGA 44.887 altura))
 (setq punretx (cons 10 p1))
 (setq punretx2 (cons 11 p12))
 (ENTMAKE (LIST '(0 . "LINE") '(100 . "AcDbEntity") '(100 . "AcDbLine") PUNRETX PUNRETX2))
 (SETQ P1 (SUMA PDESCARGA 6.58 0))
 (SETQ P12 (SUMA PDESCARGA 6.58 altura))
 (setq punretx (cons 10 p1))
 (setq punretx2 (cons 11 p12))
 (ENTMAKE (LIST '(0 . "LINE") '(100 . "AcDbEntity") '(100 . "AcDbLine") PUNRETX PUNRETX2))
 (SETQ P1 (SUMA PDESCARGA 11.922 0))
 (SETQ P12 (SUMA PDESCARGA 11.922 altura))
 (setq punretx (cons 10 p1))
 (setq punretx2 (cons 11 p12))
 (ENTMAKE (LIST '(0 . "LINE") '(100 . "AcDbEntity") '(100 . "AcDbLine") PUNRETX PUNRETX2))
 (SETQ P1 (SUMA PDESCARGA 21.042 0))
 (SETQ P12 (SUMA PDESCARGA 21.042 altura))
 (setq punretx (cons 10 p1))
 (setq punretx2 (cons 11 p12))
 (ENTMAKE (LIST '(0 . "LINE") '(100 . "AcDbEntity") '(100 . "AcDbLine") PUNRETX PUNRETX2))
 (SETQ P1 (SUMA PDESCARGA 25.933 0))
 (SETQ P12 (SUMA PDESCARGA 25.933 altura))
 (setq punretx (cons 10 p1))
 (setq punretx2 (cons 11 p12))
 (ENTMAKE (LIST '(0 . "LINE") '(100 . "AcDbEntity") '(100 . "AcDbLine") PUNRETX PUNRETX2))
 (SETQ P1 (SUMA PDESCARGA 32.694 0))
 (SETQ P12 (SUMA PDESCARGA 32.694 altura))
 (setq punretx (cons 10 p1))
 (setq punretx2 (cons 11 p12))
 (ENTMAKE (LIST '(0 . "LINE") '(100 . "AcDbEntity") '(100 . "AcDbLine") PUNRETX PUNRETX2))
 (SETQ P1 (SUMA PDESCARGA 38.842 0))
 (SETQ P12 (SUMA PDESCARGA 38.842 altura))
 (setq punretx (cons 10 p1))
 (setq punretx2 (cons 11 p12))
 (ENTMAKE (LIST '(0 . "LINE") '(100 . "AcDbEntity") '(100 . "AcDbLine") PUNRETX PUNRETX2))
 (setq cont4 cuever)
 (repeat cuever
   (COMMAND "INSERt" (STRCAT RUTA "BLOCKS\\lcd.dwg") pdescarga2 "" "" "")
   (COMMAND "EXPLODE" (ENTLASt) "")
   (COMMAND "INSERt" (STRCAT RUTA "BLOCKS\\TEXTOS SEMARNAT.dwg") pdescarga2 "" "" "")
   (COMMAND "EXPLODE" (ENTLASt) "")
   (SETQ GPOTXTP (SSGET "P"))
   (SETQ CONT3 0)
   (setq lineac (cdr (assoc cont4 matrizcuadro)))
   (REPEAT 7
      (setq atributoc (cdr (assoc cont3 lineac)))
      (SETQ ENTX (SSNAME GPOTXTP CONT3))
      (setq nte (STRCAT atributoc))
      (entmod (subst (cons 1 nte) (assoc 1 (entget entx)) (entget entx)))
      (SETQ CONT3 (1+ CONT3))
   )
   (SETQ pdescarga2 (SUMA PDESCARGA2 0 1.25))
   (setq cont4 (1- cont4))
 )
 (COMMAND "VIEW" "R" "PROV")
 (SETVAR "OSMODE" OPCIONESOS)
)

(DEFUN SUMA (P VX VY)
  (SETQ X (CAR P))
  (SETQ Y (CAR (CDR P)))
  (LIST (+ X VX) (+ Y VY) (LAST P))
)

(defun formato (datang)
  (write-line datang)
  (if (/= 1 (strlen datang))
    (progn
      (setq cuca 1)
      (while (/= cuca (strlen datang))
        (setq cara (substr datang cuca 1))
        (if (= "d" cara)
          (progn
            (setq t1 (substr datang 1 (- cuca 1)))
            (setq t2 (substr datang (+ cuca 1)))
            (setq datang2 (strcat t1 "%%d" t2))
          )
        )
        (setq cuca (+ cuca 1))
      )
      (setq datang2 datang)
    )
    (setq datang2 datang)
  )
  (setq datang datang2)
)
