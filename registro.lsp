(defun C:registro ()
  (setq name (getvar "dwgname"))
  (setq path (getvar "dwgprefix"))
  (setq version (getvar "acadver"))
  (setq fechacrea (getvar "cdate"))
  (setq fecha (getvar "date"))
  (setq ARChist (open "c:\\lisp\\histo.CSV" "a"))
  (IF (= PROGRAMA NIL)
    (SETQ PROGRAMA "DESCONOCIDO")
  )
  (SETQ LINEA (STRCAT NAME "," PATH "," VERSION "," (STRCAT (SUBSTR (RTOS FECHACREA) 7 2) "-" (SUBSTR (RTOS FECHACREA) 5 2) "-" (SUBSTR (RTOS FECHACREA) 1 4)) "," (RTOS FECHA) "," PROGRAMA))
  (WRITE-LINE LINEA ARCHIST)
  (CLOSE ARCHIST)
)
