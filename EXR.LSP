(DEFUN C:CRC ()
  (COMMAND "UNDO" "M")
  (setq GPOTEXT (ssget '((0 . "TEXT"))))
  (SETQ CONT 0)
  (SETQ E (SSNAME GPOTEXT CONT))
  (WHILE E
    (SETQ CONT2 0)
    (setq PS (cdr (assoc 1 (entget E))))
    (REPEAT 9
      (IF (WCMATCH PS (STRCAT "*/" CONT2 "/*"))
        (PROGN
        )
      )
      (SETQ CONT2 (1+ CONT2))
    )

  )
)



  (if (= (strcase OPBUS) "R")
    (if (= "ATTRIB" (cdr (assoc 0 (entget E))))
     (progn
      (SETQ REP (GETSTRING "\n TEXTO A REMPLAZAR :"))
      (setq NOMBRE (cdr (assoc 2 (entget e))))
      (SETQ LNG (STRLEN CADENAB))
      (SETQ LNG2 (STRLEN NOMBRE))
      (SETQ LNG (1- (+ INICIO LNG)))
      (SETQ P1 (- INICIO 1))
      (SETQ P2 (1+ (- LNG2 LNG)))
      (IF (< P1 0)
        (SETQ P1 (* P1 -1))
      )
      (IF (< P2 0)
        (SETQ P2 (* P2 -1))
      )
      (SETQ REMPLAZO (STRCAT (SUBSTR NOMBRE 1 P1) REP (SUBSTR NOMBRE LNG P2)))
      (COMMAND "attedit" "" "" "" "" E "V" "R" REMPLAZO "")
     )
     (progn
      (SETQ REP (GETSTRING "\n TEXTO A REMPLAZAR :"))
      (setq NOMBRE (cdr (assoc 1 (entget e))))
      (SETQ LNG (STRLEN CADENAB))
      (SETQ LNG2 (STRLEN NOMBRE))
      (SETQ LNG (1+ (+ INICIO LNG)))
      (SETQ P1 (- INICIO 1))
      (SETQ P2 (- LNG2 LNG))
      (IF (< P1 0)
        (SETQ P1 (* P1 -1))
      )
      (IF (< P2 0)
        (SETQ P2 (* P2 -1))
      )
      (SETQ REMPLAZO (STRCAT (SUBSTR NOMBRE 1 P1) REP (SUBSTR NOMBRE LNG P2)))
      (COMMAND "CHANGE" E "" "" "" "" "" "" REMPLAZO)
     )
    )
  )
