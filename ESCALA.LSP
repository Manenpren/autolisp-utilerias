(defun c:ESCALA2 ()
        (setq ARCESC (open "c:\\Archivos de Programa\\AutoCAD R14\\ESCALA.CFG" "r"))
        (IF (= ARCESC NIL)
          (SETQ ESCP 1)
         (PROGN
          (setq ESCP (read-line arcESC))
          (SETQ ESCP (ATOF ESCP))
          (IF (= ESCP NIL) (SETQ ESCP 1))
          (CLOSE ARCESC)
         )
        )
        (setq e (car (entsel "Selecciona el OBJETO a escalar: ")))
        (setq TIPO (cdr (assoc 0 (entget e))))
        (IF (= TIPO "INSERT")
         (PROGN
          (setq NOMBRE (cdr (assoc 2 (entget e))))
          (setq ESCALA (cdr (assoc 41 (entget e))))
          (setq FSN (getreal (STRCAT "DAME Porcentaje de escalamiento nuevo: <" (RTOS ESCP) ">")))
          (IF (= FSN NIL)
            (setq fsn escp)
          )
          (SETQ OP 1)
          (setq escp fsn)
         )
        )
        (if (= "TEXT" TIPO)
          (PROGN
            (setq escala (cdr (assoc 40 (entget e))))
            (SETQ LN (STRCAT "TAMA¥O ORIGINAL DEL TEXTO <" (RTOS ESCALA 2 3) ">"))
            (WRITE-LINE LN)
            (setq HF (getreal (STRCAT "TAMA¥O FINAL DEL TEXTO: <" (RTOS ESCP) ">")))
            (IF (= HF NIL)
              (setq HF escp)
            )
            (setq escp Hf)
            (SETQ OP 2)
          )
        )
        (if (AND (/= TIPO "INSERT") (/= "TEXT" TIPO))
          (PROGN
            (setq FSN (getreal (STRCAT "DAME Porcentaje de escalamiento nuevo: <" (RTOS ESCP) ">")))
            (IF (= FSN NIL)
              (setq fsn escp)
            )
            (IF (= TIPO "CIRCLE")
              (SETQ RADIO (cdr (assoc 40 (entget e))))
            )
            (SETQ OP 3)
            (setq escp fsn)
          )
        )
        (setq escgpo (ssget))
        ;(if (= sslength nil))
        (setq e (ssname escgpo 0))
        (setq t1 1)
        (IF (= OP 1)
         (while E
         (setq XYZ (cdr (assoc 10 (entget E))))
           (if (= "INSERT" (cdr (assoc 0 (entget E))))
               (if (= (strcase NOMBRE) (cdr (assoc 2 (entget E))))
                      (if (= ESCALA (cdr (assoc 41 (entget E))))
                          (command "SCALE" (cdr (assoc -1 (entget E))) "" XYZ FSN)
                      )
               )
           )
          (setq E (ssname escgpo t1))
          (setq t1 (1+ t1))
         )
        )
        (IF (= OP 2)  
         (while E
           (if (= "TEXT" (cdr (assoc 0 (entget E)))) 
               (if (= ESCALA (cdr (assoc 40 (entget E))))
               (entmod (subst (cons 40 HF) (assoc 40 (entget E)) (entget E))))
           )
          (setq E (ssname escgpo t1))
          (setq t1 (1+ t1))
         )
        )
        (IF (= OP 3)  
         (while E
           (IF (= "CIRCLE" TIPO)
            (IF (= (cdr (assoc 40 (entget E))) RADIO)
              (command "SCALE" E "" (cdr (assoc 10 (entget E))) FSN)
            )
           )
           (IF (AND (= (cdr (assoc 0 (entget E))) TIPO) (NOT (= TIPO "CIRCLE")))
             (command "SCALE" E "" (cdr (assoc 10 (entget E))) FSN)
           )
          (setq E (ssname escgpo t1))
          (setq t1 (1+ t1))
         )
        )
        (setq ARCESC (open "c:\\Archivos de Programa\\AutoCAD R14\\ESCALA.CFG" "w"))
        (WRITE-LINE (RTOS ESCP 2 3) ARCESC)
        (CLOSE ARCESC)
)
